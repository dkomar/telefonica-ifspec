GaFlexi-BWAS { 18 0 2 } DEFINITIONS ::= BEGIN

DiameterIdentity ::= OCTET STRING
Time ::= OCTET STRING
Address ::= OCTET STRING

Request ::= SEQUENCE {
	session-Id Session-Id OPTIONAL,
	origin-Host Origin-Host OPTIONAL,
	origin-Realm Origin-Realm OPTIONAL,
	destination-Realm Destination-Realm OPTIONAL,
	destination-Host Destination-Host OPTIONAL,
	accounting-Record-Type Accounting-Record-Type OPTIONAL,
	accounting-Record-Number Accounting-Record-Number OPTIONAL,
	acct-Application-Id Acct-Application-Id OPTIONAL,
	user-Name User-Name OPTIONAL,
	origin-State-Id Origin-State-Id OPTIONAL,
	event-Timestamp Event-Timestamp OPTIONAL,
	service-Context-Id Service-Context-Id OPTIONAL,
	service-Information Service-Information OPTIONAL,
	bWAS-Radius-Encoding-Version BWAS-Radius-Encoding-Version OPTIONAL,
	bWAS-Record-id BWAS-Record-id OPTIONAL,
	bWAS-Service-provider BWAS-Service-provider OPTIONAL,
	bWAS-Type BWAS-Type OPTIONAL,
	bWAS-User-Number BWAS-User-Number OPTIONAL,
	bWAS-Group-Number BWAS-Group-Number OPTIONAL,
	bWAS-Direction BWAS-Direction OPTIONAL,
	bWAS-Calling-Number BWAS-Calling-Number OPTIONAL,
	bWAS-Calling-Presentation-Indic BWAS-Calling-Presentation-Indic OPTIONAL,
	bWAS-Called-Number BWAS-Called-Number OPTIONAL,
	bWAS-Start-Time BWAS-Start-Time OPTIONAL,
	bWAS-User-Timezone BWAS-User-Timezone OPTIONAL,
	bWAS-Answer-Indic BWAS-Answer-Indic OPTIONAL,
	bWAS-Answer-Time BWAS-Answer-Time OPTIONAL,
	bWAS-Release-Time BWAS-Release-Time OPTIONAL,
	bWAS-Termination-Cause BWAS-Termination-Cause OPTIONAL,
	bWAS-Network-Type BWAS-Network-Type OPTIONAL,
	bWAS-Carrier-Identification-Code BWAS-Carrier-Identification-Code OPTIONAL,
	bWAS-Dialed-Digits BWAS-Dialed-Digits OPTIONAL,
	bWAS-Call-Category BWAS-Call-Category OPTIONAL,
	bWAS-Network-Call-Type BWAS-Network-Call-Type OPTIONAL,
	bWAS-Network-Translated-Number BWAS-Network-Translated-Number OPTIONAL,
	bWAS-Network-Translated-Group BWAS-Network-Translated-Group OPTIONAL,
	bWAS-Releasing-Party BWAS-Releasing-Party OPTIONAL,
	bWAS-Route BWAS-Route OPTIONAL,
	bWAS-Network-Callid BWAS-Network-Callid OPTIONAL,
	bWAS-Codec BWAS-Codec OPTIONAL,
	bWAS-Access-Device-Address BWAS-Access-Device-Address OPTIONAL,
	bWAS-Access-Callid BWAS-Access-Callid OPTIONAL,
	bWAS-Failover-Correlation-Id BWAS-Failover-Correlation-Id OPTIONAL,
	bWAS-Group BWAS-Group OPTIONAL,
	bWAS-Department BWAS-Department OPTIONAL,
	bWAS-Account-Code BWAS-Account-Code OPTIONAL,
	bWAS-Authorization-Code BWAS-Authorization-Code OPTIONAL,
	bWAS-Original-Called-Number BWAS-Original-Called-Number OPTIONAL,
	bWAS-Original-Called-Presentation-Indic BWAS-Original-Called-Presentation-Indic OPTIONAL,
	bWAS-Original-Called-Reason BWAS-Original-Called-Reason OPTIONAL,
	bWAS-Redirecting-Number BWAS-Redirecting-Number OPTIONAL,
	bWAS-Redirecting-Presentation-Indic BWAS-Redirecting-Presentation-Indic OPTIONAL,
	bWAS-Redirecting-Reason BWAS-Redirecting-Reason OPTIONAL,
	bWAS-Charge-Indic BWAS-Charge-Indic OPTIONAL,
	bWAS-Type-Of-Network BWAS-Type-Of-Network OPTIONAL,
	bWAS-VP-Calling-Invoke-Time BWAS-VP-Calling-Invoke-Time OPTIONAL,
	bWAS-Local-Callid BWAS-Local-Callid OPTIONAL,
	bWAS-Remote-Callid BWAS-Remote-Callid OPTIONAL,
	bWAS-Calling-Party-Category BWAS-Calling-Party-Category OPTIONAL,
	bWAS-Charging-Vector-Key BWAS-Charging-Vector-Key OPTIONAL,
	bWAS-Charging-Vector-Creator BWAS-Charging-Vector-Creator OPTIONAL,
	bWAS-Charging-Vector-Orig BWAS-Charging-Vector-Orig OPTIONAL,
	bWAS-Charging-Vector-Term BWAS-Charging-Vector-Term OPTIONAL,
	bWAS-Acc-Per-Call-Invoke-Time BWAS-Acc-Per-Call-Invoke-Time OPTIONAL,
	bWAS-Acc-Per-Call-Fac-Result BWAS-Acc-Per-Call-Fac-Result OPTIONAL,
	bWAS-Acb-Act-Invoke-Time BWAS-Acb-Act-Invoke-Time OPTIONAL,
	bWAS-Acb-Act-Fac-Result BWAS-Acb-Act-Fac-Result OPTIONAL,
	bWAS-Acb-Deact-Invoke-Time BWAS-Acb-Deact-Invoke-Time OPTIONAL,
	bWAS-Acb-Deact-Fac-Result BWAS-Acb-Deact-Fac-Result OPTIONAL,
	bWAS-Call-Park-Invoke-Time BWAS-Call-Park-Invoke-Time OPTIONAL,
	bWAS-Call-Park-Fac-Result BWAS-Call-Park-Fac-Result OPTIONAL,
	bWAS-Call-Park-Retr-Invoke-Time BWAS-Call-Park-Retr-Invoke-Time OPTIONAL,
	bWAS-Call-Park-Retr-Fac-Result BWAS-Call-Park-Retr-Fac-Result OPTIONAL,
	bWAS-Call-Pickup-Invoke-Time BWAS-Call-Pickup-Invoke-Time OPTIONAL,
	bWAS-Call-Pickup-Fac-Result BWAS-Call-Pickup-Fac-Result OPTIONAL,
	bWAS-Directed-Call-Pickup-Invoke-Time BWAS-Directed-Call-Pickup-Invoke-Time OPTIONAL,
	bWAS-Directed-Call-Pickup-Fac-Result BWAS-Directed-Call-Pickup-Fac-Result OPTIONAL,
	bWAS-Dpubi-Invoke-Time BWAS-Dpubi-Invoke-Time OPTIONAL,
	bWAS-Dpubi-Fac-Result BWAS-Dpubi-Fac-Result OPTIONAL,
	bWAS-Cancel-Cwt-Per-Call-Invoke-Time BWAS-Cancel-Cwt-Per-Call-Invoke-Time OPTIONAL,
	bWAS-Cancel-Cwt-Per-Call-Fac-Result BWAS-Cancel-Cwt-Per-Call-Fac-Result OPTIONAL,
	bWAS-Cfa-Act-Invoke-Time BWAS-Cfa-Act-Invoke-Time OPTIONAL,
	bWAS-Cfa-Act-Fac-Result BWAS-Cfa-Act-Fac-Result OPTIONAL,
	bWAS-Cfa-Deact-Invoke-Time BWAS-Cfa-Deact-Invoke-Time OPTIONAL,
	bWAS-Cfa-Deact-Fac-Result BWAS-Cfa-Deact-Fac-Result OPTIONAL,
	bWAS-Cfb-Act-Invoke-Time BWAS-Cfb-Act-Invoke-Time OPTIONAL,
	bWAS-Cfb-Act-Fac-Result BWAS-Cfb-Act-Fac-Result OPTIONAL,
	bWAS-Cfb-Deact-Invoke-Time BWAS-Cfb-Deact-Invoke-Time OPTIONAL,
	bWAS-Cfb-Deact-Fac-Result BWAS-Cfb-Deact-Fac-Result OPTIONAL,
	bWAS-Cfna-Act-Invoke-Time BWAS-Cfna-Act-Invoke-Time OPTIONAL,
	bWAS-Cfna-Act-Fac-Result BWAS-Cfna-Act-Fac-Result OPTIONAL,
	bWAS-Cfna-Deact-Invoke-Time BWAS-Cfna-Deact-Invoke-Time OPTIONAL,
	bWAS-Cfna-Deact-Fac-Result BWAS-Cfna-Deact-Fac-Result OPTIONAL,
	bWAS-Clid-Delivery-Per-Call-Invoke-Time BWAS-Clid-Delivery-Per-Call-Invoke-Time OPTIONAL,
	bWAS-Clid-Delivery-Per-Call-Fac-Result BWAS-Clid-Delivery-Per-Call-Fac-Result OPTIONAL,
	bWAS-Clid-Blocking-Per-Call-Invoke-Time BWAS-Clid-Blocking-Per-Call-Invoke-Time OPTIONAL,
	bWAS-Clid-Blocking-Per-Call-Fac-Result BWAS-Clid-Blocking-Per-Call-Fac-Result OPTIONAL,
	bWAS-Cot-Invoke-Time BWAS-Cot-Invoke-Time OPTIONAL,
	bWAS-Cot-Fac-Result BWAS-Cot-Fac-Result OPTIONAL,
	bWAS-Direct-Vm-Xfer-Invoke-Time BWAS-Direct-Vm-Xfer-Invoke-Time OPTIONAL,
	bWAS-Direct-Vm-Xfer-Fac-Result BWAS-Direct-Vm-Xfer-Fac-Result OPTIONAL,
	bWAS-Dnd-Act-Invoke-Time BWAS-Dnd-Act-Invoke-Time OPTIONAL,
	bWAS-Dnd-Act-Fac-Result BWAS-Dnd-Act-Fac-Result OPTIONAL,
	bWAS-Dnd-Deact-Invoke-Time BWAS-Dnd-Deact-Invoke-Time OPTIONAL,
	bWAS-Dnd-Deact-Fac-Result BWAS-Dnd-Deact-Fac-Result OPTIONAL,
	bWAS-Sac-Lock-Invoke-Time BWAS-Sac-Lock-Invoke-Time OPTIONAL,
	bWAS-Sac-Lock-Fac-Result BWAS-Sac-Lock-Fac-Result OPTIONAL,
	bWAS-Sac-Unlock-Invoke-Time BWAS-Sac-Unlock-Invoke-Time OPTIONAL,
	bWAS-Sac-Unlock-Fac-Result BWAS-Sac-Unlock-Fac-Result OPTIONAL,
	bWAS-Flash-Call-Hold-Invoke-Time BWAS-Flash-Call-Hold-Invoke-Time OPTIONAL,
	bWAS-Flash-Call-Hold-Fac-Result BWAS-Flash-Call-Hold-Fac-Result OPTIONAL,
	bWAS-Last-Number-Redial-Invoke-Time BWAS-Last-Number-Redial-Invoke-Time OPTIONAL,
	bWAS-Last-Number-Redial-Fac-Result BWAS-Last-Number-Redial-Fac-Result OPTIONAL,
	bWAS-Return-Call-Invoke-Time BWAS-Return-Call-Invoke-Time OPTIONAL,
	bWAS-Return-Call-Fac-Result BWAS-Return-Call-Fac-Result OPTIONAL,
	bWAS-Sd100-Programming-Invoke-Time BWAS-Sd100-Programming-Invoke-Time OPTIONAL,
	bWAS-Sd100-Programming-Fac-Result BWAS-Sd100-Programming-Fac-Result OPTIONAL,
	bWAS-Sd8-Programming-Invoke-Time BWAS-Sd8-Programming-Invoke-Time OPTIONAL,
	bWAS-Sd8-Programming-Fac-Result BWAS-Sd8-Programming-Fac-Result OPTIONAL,
	bWAS-Clear-Mwi-Invoke-Time BWAS-Clear-Mwi-Invoke-Time OPTIONAL,
	bWAS-Clear-Mwi-Fac-Result BWAS-Clear-Mwi-Fac-Result OPTIONAL,
	bWAS-UserId BWAS-UserId OPTIONAL,
	bWAS-Other-Party-Name BWAS-Other-Party-Name OPTIONAL,
	bWAS-Other-Party-Name-Pres-Indic BWAS-Other-Party-Name-Pres-Indic OPTIONAL,
	bWAS-Moh-Deact-Invoke-Time BWAS-Moh-Deact-Invoke-Time OPTIONAL,
	bWAS-Moh-Deact-Fac-Result BWAS-Moh-Deact-Fac-Result OPTIONAL,
	bWAS-Push-to-Talk-Invoke-Time BWAS-Push-to-Talk-Invoke-Time OPTIONAL,
	bWAS-Push-to-Talk-Fac-Result BWAS-Push-to-Talk-Fac-Result OPTIONAL,
	bWAS-Hoteling-Invoke-Time BWAS-Hoteling-Invoke-Time OPTIONAL,
	bWAS-Hoteling-Group BWAS-Hoteling-Group OPTIONAL,
	bWAS-Hoteling-UserId BWAS-Hoteling-UserId OPTIONAL,
	bWAS-Hoteling-User-Number BWAS-Hoteling-User-Number OPTIONAL,
	bWAS-Hoteling-Group-Number BWAS-Hoteling-Group-Number OPTIONAL,
	bWAS-Diversion-Inhibitor-Invoke-time BWAS-Diversion-Inhibitor-Invoke-time OPTIONAL,
	bWAS-Diversion-Inhibitor-Fac-Result BWAS-Diversion-Inhibitor-Fac-Result OPTIONAL,
	bWAS-Trunk-Group-Name BWAS-Trunk-Group-Name OPTIONAL,
	bWAS-InstantGroupCall-Invoke-Time BWAS-InstantGroupCall-Invoke-Time OPTIONAL,
	bWAS-InstantGroupCall-PushToTalk BWAS-InstantGroupCall-PushToTalk OPTIONAL,
	bWAS-InstantGroupCall-Related-Callid BWAS-InstantGroupCall-Related-Callid OPTIONAL,
	bWAS-CustomRingback-Invoke-Time BWAS-CustomRingback-Invoke-Time OPTIONAL,
	bWAS-CLID-Permitted BWAS-CLID-Permitted OPTIONAL,
	bWAS-AHR-Invoke-Time BWAS-AHR-Invoke-Time OPTIONAL,
	bWAS-AHR-Action BWAS-AHR-Action OPTIONAL,
	bWAS-Access-Network-Info BWAS-Access-Network-Info OPTIONAL,
	bWAS-Charging-Function-Addresses BWAS-Charging-Function-Addresses OPTIONAL,
	bWAS-Charge-Number BWAS-Charge-Number OPTIONAL,
	bWAS-Related-CallId BWAS-Related-CallId OPTIONAL,
	bWAS-Related-CallId-Reason BWAS-Related-CallId-Reason OPTIONAL,
	bWAS-Transfer-Invoke-Time BWAS-Transfer-Invoke-Time OPTIONAL,
	bWAS-Transfer-Result BWAS-Transfer-Result OPTIONAL,
	bWAS-Transfer-Related-CallId BWAS-Transfer-Related-CallId OPTIONAL,
	bWAS-Transfer-Type BWAS-Transfer-Type OPTIONAL,
	bWAS-Conf-Start-Time BWAS-Conf-Start-Time OPTIONAL,
	bWAS-Conf-Stop-Time BWAS-Conf-Stop-Time OPTIONAL,
	bWAS-Conf-Id BWAS-Conf-Id OPTIONAL,
	bWAS-Conf-Type BWAS-Conf-Type OPTIONAL,
	bWAS-Codec-Usage BWAS-Codec-Usage OPTIONAL,
	bWAS-Vmb-Act-Invoke-Time BWAS-Vmb-Act-Invoke-Time OPTIONAL,
	bWAS-Vmb-Act-Fac-Result BWAS-Vmb-Act-Fac-Result OPTIONAL,
	bWAS-Vmb-Deact-Invoke-Time BWAS-Vmb-Deact-Invoke-Time OPTIONAL,
	bWAS-Vmb-Deact-Fac-Result BWAS-Vmb-Deact-Fac-Result OPTIONAL,
	bWAS-Vmna-Act-Invoke-Time BWAS-Vmna-Act-Invoke-Time OPTIONAL,
	bWAS-Vmna-Act-Fac-Result BWAS-Vmna-Act-Fac-Result OPTIONAL,
	bWAS-Vmna-Deact-Invoke-Time BWAS-Vmna-Deact-Invoke-Time OPTIONAL,
	bWAS-Vmna-Deact-Fac-Result BWAS-Vmna-Deact-Fac-Result OPTIONAL,
	bWAS-Vma-Act-Invoke-Time BWAS-Vma-Act-Invoke-Time OPTIONAL,
	bWAS-Vma-Act-Fac-Result BWAS-Vma-Act-Fac-Result OPTIONAL,
	bWAS-Vma-Deact-Invoke-Time BWAS-Vma-Deact-Invoke-Time OPTIONAL,
	bWAS-Vma-Deact-Fac-Result BWAS-Vma-Deact-Fac-Result OPTIONAL,
	bWAS-No-Answer-Set-Invoke-Time BWAS-No-Answer-Set-Invoke-Time OPTIONAL,
	bWAS-No-Answer-Set-Fac-Result BWAS-No-Answer-Set-Fac-Result OPTIONAL,
	bWAS-Clid-Blocking-Act-Invoke-Time BWAS-Clid-Blocking-Act-Invoke-Time OPTIONAL,
	bWAS-Clid-Blocking-Act-Fac-Result BWAS-Clid-Blocking-Act-Fac-Result OPTIONAL,
	bWAS-Clid-Blocking-Deact-Invoke-Time BWAS-Clid-Blocking-Deact-Invoke-Time OPTIONAL,
	bWAS-Clid-Blocking-Deact-Fac-Result BWAS-Clid-Blocking-Deact-Fac-Result OPTIONAL,
	bWAS-Call-Waiting-Act-Invoke-Time BWAS-Call-Waiting-Act-Invoke-Time OPTIONAL,
	bWAS-Call-Waiting-Act-Fac-Result BWAS-Call-Waiting-Act-Fac-Result OPTIONAL,
	bWAS-Call-Waiting-Deact-Invoke-Time BWAS-Call-Waiting-Deact-Invoke-Time OPTIONAL,
	bWAS-Call-Waiting-Deact-Fac-Result BWAS-Call-Waiting-Deact-Fac-Result OPTIONAL,
	bWAS-Fax-Messaging BWAS-Fax-Messaging OPTIONAL,
	bWAS-TSD-Digits BWAS-TSD-Digits OPTIONAL,
	bWAS-Trunk-Group-Info BWAS-Trunk-Group-Info OPTIONAL,
	bWAS-Recall-Type BWAS-Recall-Type OPTIONAL,
	bWAS-Cfnrc-Act-Invoke-Time BWAS-Cfnrc-Act-Invoke-Time OPTIONAL,
	bWAS-Cfnrc-Act-Fac-Result BWAS-Cfnrc-Act-Fac-Result OPTIONAL,
	bWAS-Cfnrc-Deact-Invoke-Time BWAS-Cfnrc-Deact-Invoke-Time OPTIONAL,
	bWAS-Cfnrc-Deact-Fac-Result BWAS-Cfnrc-Deact-Fac-Result OPTIONAL,
	bWAS-Q850-Cause BWAS-Q850-Cause OPTIONAL,
	bWAS-Dialed-Digits-Context BWAS-Dialed-Digits-Context OPTIONAL,
	bWAS-Called-Number-Context BWAS-Called-Number-Context OPTIONAL,
	bWAS-Network-Translated-Number-Context BWAS-Network-Translated-Number-Context OPTIONAL,
	bWAS-Calling-Number-Context BWAS-Calling-Number-Context OPTIONAL,
	bWAS-Original-Called-Number-Context BWAS-Original-Called-Number-Context OPTIONAL,
	bWAS-Redirecting-Number-Context BWAS-Redirecting-Number-Context OPTIONAL,
	bWAS-Location-Control-Act-Result BWAS-Location-Control-Act-Result OPTIONAL,
	bWAS-Location-Control-Deact-Result BWAS-Location-Control-Deact-Result OPTIONAL,
	bWAS-Call-Retrieve-Result BWAS-Call-Retrieve-Result OPTIONAL,
	bWAS-Routing-Number BWAS-Routing-Number OPTIONAL,
	bWAS-Origination-Method BWAS-Origination-Method OPTIONAL,
	bWAS-Call-Parked-Invoke-Time BWAS-Call-Parked-Invoke-Time OPTIONAL,
	bWAS-BA-Related-Call-Id BWAS-BA-Related-Call-Id OPTIONAL,
	bWAS-Acr-Act-Invoke-Time BWAS-Acr-Act-Invoke-Time OPTIONAL,
	bWAS-Acr-Act-Fac-Result BWAS-Acr-Act-Fac-Result OPTIONAL,
	bWAS-Acr-Deact-Invoke-Time BWAS-Acr-Deact-Invoke-Time OPTIONAL,
	bWAS-Acr-Deact-Fac-Result BWAS-Acr-Deact-Fac-Result OPTIONAL,
	bWAS-Outside-Access-Code BWAS-Outside-Access-Code OPTIONAL,
	bWAS-Primary-Device-Line-Port BWAS-Primary-Device-Line-Port OPTIONAL,
	bWAS-Called-Asserted-Identity BWAS-Called-Asserted-Identity OPTIONAL,
	bWAS-Called-Asserted-Pres-Indicator BWAS-Called-Asserted-Pres-Indicator OPTIONAL,
	bWAS-SDP BWAS-SDP OPTIONAL,
	bWAS-Media-Initiator-Flag BWAS-Media-Initiator-Flag OPTIONAL,
	bWAS-SDP-Offer-Timestamp BWAS-SDP-Offer-Timestamp OPTIONAL,
	bWAS-SDP-Answer-Timestamp BWAS-SDP-Answer-Timestamp OPTIONAL,
	bWAS-Early-Media-SDP BWAS-Early-Media-SDP OPTIONAL,
	bWAS-Early-Media-Initiator-Flag BWAS-Early-Media-Initiator-Flag OPTIONAL,
	bWAS-Body-Content-Type BWAS-Body-Content-Type OPTIONAL,
	bWAS-Body-Content-Length BWAS-Body-Content-Length OPTIONAL,
	bWAS-Body-Content-Disposition BWAS-Body-Content-Disposition OPTIONAL,
	bWAS-Body-Originator BWAS-Body-Originator OPTIONAL,
	bWAS-SIP-Error-Code BWAS-SIP-Error-Code OPTIONAL,
	bWAS-otherInfoInPCV BWAS-otherInfoInPCV OPTIONAL,
	bWAS-Received-Calling-Number BWAS-Received-Calling-Number OPTIONAL,
	bWAS-CustomRingback-Media-Selection BWAS-CustomRingback-Media-Selection OPTIONAL,
	bWAS-AOC-Type BWAS-AOC-Type OPTIONAL,
	bWAS-AOC-Charge BWAS-AOC-Charge OPTIONAL,
	bWAS-AOC-Currency BWAS-AOC-Currency OPTIONAL,
	bWAS-AOC-Time BWAS-AOC-Time OPTIONAL,
	bWAS-AOC-Sum BWAS-AOC-Sum OPTIONAL,
	bWAS-AOC-Activation-Time BWAS-AOC-Activation-Time OPTIONAL,
	bWAS-AOC-Result BWAS-AOC-Result OPTIONAL,
	bWAS-AS-Call-Type BWAS-AS-Call-Type OPTIONAL,
	bWAS-Scf-Act-Invoke-Time BWAS-Scf-Act-Invoke-Time OPTIONAL,
	bWAS-Scf-Act-Fac-Result BWAS-Scf-Act-Fac-Result OPTIONAL,
	bWAS-Scf-Deact-Invoke-Time BWAS-Scf-Deact-Invoke-Time OPTIONAL,
	bWAS-Scf-Deact-Fac-Result BWAS-Scf-Deact-Fac-Result OPTIONAL,
	bWAS-Cfa-Inter-Invoke-Time BWAS-Cfa-Inter-Invoke-Time OPTIONAL,
	bWAS-Cfa-Inter-Fac-Result BWAS-Cfa-Inter-Fac-Result OPTIONAL,
	bWAS-Cfna-Inter-Invoke-Time BWAS-Cfna-Inter-Invoke-Time OPTIONAL,
	bWAS-Cfna-Inter-Fac-Result BWAS-Cfna-Inter-Fac-Result OPTIONAL,
	bWAS-Cfb-Inter-Invoke-Time BWAS-Cfb-Inter-Invoke-Time OPTIONAL,
	bWAS-Cfb-Inter-Fac-Result BWAS-Cfb-Inter-Fac-Result OPTIONAL,
	bWAS-CBF-Auth-Code BWAS-CBF-Auth-Code OPTIONAL,
	bWAS-Call-Bridge-Result BWAS-Call-Bridge-Result OPTIONAL,
	bWAS-Return-Call-Number-Deletion-Invoke-Time BWAS-Return-Call-Number-Deletion-Invoke-Time OPTIONAL,
	bWAS-Return-Call-Number-Deletion-Fac-Result BWAS-Return-Call-Number-Deletion-Fac-Result OPTIONAL,
	bWAS-Prepaid-Status BWAS-Prepaid-Status OPTIONAL,
	bWAS-Configurable-CLID BWAS-Configurable-CLID OPTIONAL,
	bWAS-Call-Center-Night-Service-Act-Result BWAS-Call-Center-Night-Service-Act-Result OPTIONAL,
	bWAS-Call-Center-Night-Service-Deact-Result BWAS-Call-Center-Night-Service-Deact-Result OPTIONAL,
	bWAS-Call-Center-Forced-Forwarding-Act-Result BWAS-Call-Center-Forced-Forwarding-Act-Result OPTIONAL,
	bWAS-Call-Center-Forced-Forwarding-Deact-Result BWAS-Call-Center-Forced-Forwarding-Deact-Result OPTIONAL,
	bWAS-Call-Center-Outgoing-Call-FAC-Result BWAS-Call-Center-Outgoing-Call-FAC-Result OPTIONAL,
	bWAS-Call-Center-Outgoing-Personal-Call-FAC-Result BWAS-Call-Center-Outgoing-Personal-Call-FAC-Result OPTIONAL,
	bWAS-Call-Center-Outgoing-Phone-Number BWAS-Call-Center-Outgoing-Phone-Number OPTIONAL,
	bWAS-Intercept-User-Routing-Number BWAS-Intercept-User-Routing-Number OPTIONAL,
	bWAS-Intercept-Group-Routing-Number BWAS-Intercept-Group-Routing-Number OPTIONAL,
	bWAS-CB-Activation-Invoke-Time BWAS-CB-Activation-Invoke-Time OPTIONAL,
	bWAS-CB-Activation-Fac-Result BWAS-CB-Activation-Fac-Result OPTIONAL,
	bWAS-CB-Deactivation-Invoke-Time BWAS-CB-Deactivation-Invoke-Time OPTIONAL,
	bWAS-CB-Deactivation-Fac-Result BWAS-CB-Deactivation-Fac-Result OPTIONAL,
	bWAS-CB-Query-Invoke-Time BWAS-CB-Query-Invoke-Time OPTIONAL,
	bWAS-CB-Query-Fac-Result BWAS-CB-Query-Fac-Result OPTIONAL,
	bWAS-Cfnrc-Inter-Invoke-Time BWAS-Cfnrc-Inter-Invoke-Time OPTIONAL,
	bWAS-Cfnrc-Inter-Fac-Result BWAS-Cfnrc-Inter-Fac-Result OPTIONAL,
	bWAS-VMR-Dialing-Invoke-Time BWAS-VMR-Dialing-Invoke-Time OPTIONAL,
	bWAS-VMR-Dialing-Fac-result BWAS-VMR-Dialing-Fac-result OPTIONAL,
	bWAS-VP-Dialing-Invoke-Time BWAS-VP-Dialing-Invoke-Time OPTIONAL,
	bWAS-VP-Dialing-Fac-result BWAS-VP-Dialing-Fac-result OPTIONAL,
	bWAS-Camel-Loc-Info BWAS-Camel-Loc-Info OPTIONAL,
	bWAS-Camel-Msc-Address BWAS-Camel-Msc-Address OPTIONAL,
	bWAS-Camel-CellId-Or-LAI BWAS-Camel-CellId-Or-LAI OPTIONAL,
	bWAS-NAME-Permitted BWAS-NAME-Permitted OPTIONAL,
	bWAS-Call-Center-User-Id BWAS-Call-Center-User-Id OPTIONAL,
	bWAS-Call-Center-Outgoing-Group-Phone-Number BWAS-Call-Center-Outgoing-Group-Phone-Number OPTIONAL,
	bWAS-VON-Type BWAS-VON-Type OPTIONAL,
	bWAS-PreAlertingAnncmtDuration BWAS-PreAlertingAnncmtDuration OPTIONAL,
	bWAS-CC-Disp-Code-Tagging-Invoke-Time BWAS-CC-Disp-Code-Tagging-Invoke-Time OPTIONAL,
	bWAS-CC-Disp-Code-Tagging-Result BWAS-CC-Disp-Code-Tagging-Result OPTIONAL,
	bWAS-CC-Escalated-Call-Invoke-Time BWAS-CC-Escalated-Call-Invoke-Time OPTIONAL,
	bWAS-CC-Escalated-Call-FAC-Result BWAS-CC-Escalated-Call-FAC-Result OPTIONAL,
	bWAS-CC-Monitoring-BI-Invoke-Time BWAS-CC-Monitoring-BI-Invoke-Time OPTIONAL,
	bWAS-CC-Monitoring-BI-FAC-Result BWAS-CC-Monitoring-BI-FAC-Result OPTIONAL,
	bWAS-Mid-Call-Cot-Invoke-Time BWAS-Mid-Call-Cot-Invoke-Time OPTIONAL,
	bWAS-Office-Zone BWAS-Office-Zone OPTIONAL,
	bWAS-Primary-Zone BWAS-Primary-Zone OPTIONAL,
	bWAS-Roaming-MSC-Address BWAS-Roaming-MSC-Address OPTIONAL,
	bWAS-CC-Emergency-Call-Invoke-Time BWAS-CC-Emergency-Call-Invoke-Time OPTIONAL,
	bWAS-Monitoring-Next-Call-Invoke-Time BWAS-Monitoring-Next-Call-Invoke-Time OPTIONAL,
	bWAS-Monitoring-Next-Call-FAC-Result BWAS-Monitoring-Next-Call-FAC-Result OPTIONAL,
	bWAS-Legacy-Acb-Act-Invoke-Time BWAS-Legacy-Acb-Act-Invoke-Time OPTIONAL,
	bWAS-Legacy-Acb-Act-Fac-Result BWAS-Legacy-Acb-Act-Fac-Result OPTIONAL,
	bWAS-Legacy-Acb-Deact-Invoke-Time BWAS-Legacy-Acb-Deact-Invoke-Time OPTIONAL,
	bWAS-Legacy-Acb-Deact-Fac-Result BWAS-Legacy-Acb-Deact-Fac-Result OPTIONAL,
	bWAS-Custom-Schema-Version BWAS-Custom-Schema-Version OPTIONAL,
	bWAS-Group-Paging-Invoke-Time BWAS-Group-Paging-Invoke-Time OPTIONAL,
	bWAS-Group-Paging-Related-CallId BWAS-Group-Paging-Related-CallId OPTIONAL,
	bWAS-DCLID BWAS-DCLID OPTIONAL,
	bWAS-MeetMeConferencing-InvokeTime BWAS-MeetMeConferencing-InvokeTime OPTIONAL,
	bWAS-Call-Me-Now-Type BWAS-Call-Me-Now-Type OPTIONAL,
	bWAS-Call-Me-Now-Transaction-Id BWAS-Call-Me-Now-Transaction-Id OPTIONAL,
	bWAS-Call-Me-Now-Related-Call-Id BWAS-Call-Me-Now-Related-Call-Id OPTIONAL,
	bWAS-MeetMeConferencing-ConferenceId BWAS-MeetMeConferencing-ConferenceId OPTIONAL,
	bWAS-MeetMeConferencing-Role BWAS-MeetMeConferencing-Role OPTIONAL,
	bWAS-MeetMeConferencing-Bridge BWAS-MeetMeConferencing-Bridge OPTIONAL,
	bWAS-MeetMeConferencing-Owner BWAS-MeetMeConferencing-Owner OPTIONAL,
	bWAS-MeetMeConferencing-OwnerDn BWAS-MeetMeConferencing-OwnerDn OPTIONAL,
	bWAS-MeetMeConferencing-Title BWAS-MeetMeConferencing-Title OPTIONAL,
	bWAS-MeetMeConferencing-ProjectCode BWAS-MeetMeConferencing-ProjectCode OPTIONAL,
	bWAS-MeetMeConferencing-RecordDuration BWAS-MeetMeConferencing-RecordDuration OPTIONAL,
	bWAS-MobilityNumber BWAS-MobilityNumber OPTIONAL,
	bWAS-MobilityRoutingNumber BWAS-MobilityRoutingNumber OPTIONAL,
	bWAS-Location BWAS-Location OPTIONAL,
	bWAS-Location-Type BWAS-Location-Type OPTIONAL,
	bWAS-Location-Usage BWAS-Location-Usage OPTIONAL,
	bWAS-Call-Recording-Invocation-Time BWAS-Call-Recording-Invocation-Time OPTIONAL,
	bWAS-Call-Recording-FAC-Result BWAS-Call-Recording-FAC-Result OPTIONAL,
	bWAS-Call-Recording-Trigger BWAS-Call-Recording-Trigger OPTIONAL,
	bWAS-Call-Recording-Destination BWAS-Call-Recording-Destination OPTIONAL,
	bWAS-Call-Recording-Result BWAS-Call-Recording-Result OPTIONAL,
	bWAS-Calling-Pres-Number BWAS-Calling-Pres-Number OPTIONAL,
	bWAS-Calling-Pres-Number-Context BWAS-Calling-Pres-Number-Context OPTIONAL,
	bWAS-Calling-Asserted-Number BWAS-Calling-Asserted-Number OPTIONAL,
	bWAS-Calling-Asserted-Number-Context BWAS-Calling-Asserted-Number-Context OPTIONAL,
	bWAS-SCC-Invocation-Time BWAS-SCC-Invocation-Time OPTIONAL,
	bWAS-SCC-Call-Id BWAS-SCC-Call-Id OPTIONAL,
	bWAS-SCC-Number BWAS-SCC-Number OPTIONAL,
	bWAS-Acr-Inter-Invoke-Time BWAS-Acr-Inter-Invoke-Time OPTIONAL,
	bWAS-Acr-Inter-Fac-Result BWAS-Acr-Inter-Fac-Result OPTIONAL,
	bWAS-CW-Inter-Invoke-Time BWAS-CW-Inter-Invoke-Time OPTIONAL,
	bWAS-CW-Inter-Fac-Result BWAS-CW-Inter-Fac-Result OPTIONAL,
	bWAS-Clid-Blocking-Inter-Invoke-Time BWAS-Clid-Blocking-Inter-Invoke-Time OPTIONAL,
	bWAS-Clid-Blocking-Inter-Fac-Result BWAS-Clid-Blocking-Inter-Fac-Result OPTIONAL,
	bWAS-Colr-Inter-Invoke-Time BWAS-Colr-Inter-Invoke-Time OPTIONAL,
	bWAS-Colr-Inter-Fac-Result BWAS-Colr-Inter-Fac-Result OPTIONAL,
	bWAS-Scr-Inter-Invoke-Time BWAS-Scr-Inter-Invoke-Time OPTIONAL,
	bWAS-Scr-Inter-Fac-Result BWAS-Scr-Inter-Fac-Result OPTIONAL,
	bWAS-User-Agent BWAS-User-Agent OPTIONAL,
	bWAS-FMFM-Call-Push-Invocation-Time BWAS-FMFM-Call-Push-Invocation-Time OPTIONAL,
	bWAS-FMFM-Call-Push-FAC-Result BWAS-FMFM-Call-Push-FAC-Result OPTIONAL
}
Session-Id ::= [263] UTF8String
Origin-Host ::= [264] DiameterIdentity
Origin-Realm ::= [296] DiameterIdentity
Destination-Realm ::= [283] DiameterIdentity
Destination-Host ::= [293] DiameterIdentity
Accounting-Record-Type ::= [480] INTEGER
Accounting-Record-Number ::= [485] INTEGER
Acct-Application-Id ::= [259] INTEGER
User-Name ::= [1] UTF8String
Origin-State-Id ::= [278] INTEGER
Event-Timestamp ::= [55] Time
Service-Context-Id ::= [461] UTF8String
Service-Information ::= [341279593] SEQUENCE {
	subscription-Id Subscription-Id OPTIONAL,
	iMS-Information IMS-Information OPTIONAL
}
Subscription-Id ::= [443] SEQUENCE {
	subscription-Id-Type Subscription-Id-Type OPTIONAL,
	subscription-Id-Data Subscription-Id-Data OPTIONAL
}
Subscription-Id-Type ::= [450] INTEGER
Subscription-Id-Data ::= [444] UTF8String
IMS-Information ::= [341279596] SEQUENCE {
	event-Type Event-Type OPTIONAL,
	node-Functionality Node-Functionality OPTIONAL,
	role-of-Node Role-of-Node OPTIONAL,
	user-Session-Id User-Session-Id OPTIONAL,
	calling-Party-Address Calling-Party-Address OPTIONAL,
	called-Party-Address Called-Party-Address OPTIONAL,
	called-Asserted-Identity Called-Asserted-Identity OPTIONAL,
	time-Stamps Time-Stamps OPTIONAL,
	inter-Operator-Identifier Inter-Operator-Identifier OPTIONAL,
	iMS-Charging-Identifier IMS-Charging-Identifier OPTIONAL,
	early-Media-Description SEQUENCE OF Early-Media-Description OPTIONAL,
	sDP-Session-Description SEQUENCE OF SDP-Session-Description OPTIONAL,
	sDP-Media-Component SEQUENCE OF SDP-Media-Component OPTIONAL,
	message-Bodies SEQUENCE OF Message-Bodies OPTIONAL,
	access-Network-Information Access-Network-Information OPTIONAL,
	cause-Code Cause-Code OPTIONAL
}
Event-Type ::= [341279543] SEQUENCE {
	sIP-Method SIP-Method OPTIONAL
}
SIP-Method ::= [341279544] UTF8String
Node-Functionality ::= [341279582] INTEGER
Role-of-Node ::= [341279549] INTEGER
User-Session-Id ::= [341279550] UTF8String
Calling-Party-Address ::= [341279551] UTF8String
Called-Party-Address ::= [341279552] UTF8String
Called-Asserted-Identity ::= [341279970] UTF8String
Time-Stamps ::= [341279553] SEQUENCE {
	sIP-Request-Timestamp SIP-Request-Timestamp OPTIONAL,
	sIP-Response-Timestamp SIP-Response-Timestamp OPTIONAL
}
SIP-Request-Timestamp ::= [341279554] Time
SIP-Response-Timestamp ::= [341279555] Time
Inter-Operator-Identifier ::= [341279558] SEQUENCE {
	originating-IOI Originating-IOI OPTIONAL,
	terminating-IOI Terminating-IOI OPTIONAL
}
Originating-IOI ::= [341279559] UTF8String
Terminating-IOI ::= [341279560] UTF8String
IMS-Charging-Identifier ::= [341279561] UTF8String
Early-Media-Description ::= [341279992] SEQUENCE {
	sDP-TimeStamps SDP-TimeStamps OPTIONAL,
	sDP-Media-Component SEQUENCE OF SDP-Media-Component OPTIONAL,
	sDP-Session-Description SEQUENCE OF SDP-Session-Description OPTIONAL
}
SDP-TimeStamps ::= [341279993] SEQUENCE {
	sDP-Offer-Timestamp SDP-Offer-Timestamp OPTIONAL,
	sDP-Answer-Timestamp SDP-Answer-Timestamp OPTIONAL
}
SDP-Offer-Timestamp ::= [341279994] Time
SDP-Answer-Timestamp ::= [341279995] Time
SDP-Media-Component ::= [341279563] SEQUENCE {
	sDP-Media-Name SDP-Media-Name OPTIONAL,
	sDP-Media-Description SEQUENCE OF SDP-Media-Description OPTIONAL,
	media-Initiator-Flag Media-Initiator-Flag OPTIONAL
}
SDP-Media-Name ::= [341279564] UTF8String
SDP-Media-Description ::= [341279565] UTF8String
Media-Initiator-Flag ::= [341279602] INTEGER
SDP-Session-Description ::= [341279562] UTF8String
Message-Bodies ::= [341279609] SEQUENCE {
	content-Type Content-Type OPTIONAL,
	content-Length Content-Length OPTIONAL,
	content-Disposition Content-Disposition OPTIONAL,
	originator Originator OPTIONAL
}
Content-Type ::= [341279546] UTF8String
Content-Length ::= [341279547] INTEGER
Content-Disposition ::= [341279548] UTF8String
Originator ::= [341279584] INTEGER
Access-Network-Information ::= [341279983] OCTET STRING
Cause-Code ::= [341279581] INTEGER
BWAS-Radius-Encoding-Version ::= [210731008] UTF8String
BWAS-Record-id ::= [210731009] UTF8String
BWAS-Service-provider ::= [210731010] UTF8String
BWAS-Type ::= [210731011] UTF8String
BWAS-User-Number ::= [210731012] UTF8String
BWAS-Group-Number ::= [210731013] UTF8String
BWAS-Direction ::= [210731014] UTF8String
BWAS-Calling-Number ::= [210731015] UTF8String
BWAS-Calling-Presentation-Indic ::= [210731016] UTF8String
BWAS-Called-Number ::= [210731017] UTF8String
BWAS-Start-Time ::= [210731018] UTF8String
BWAS-User-Timezone ::= [210731019] UTF8String
BWAS-Answer-Indic ::= [210731020] UTF8String
BWAS-Answer-Time ::= [210731021] UTF8String
BWAS-Release-Time ::= [210731022] UTF8String
BWAS-Termination-Cause ::= [210731023] UTF8String
BWAS-Network-Type ::= [210731024] UTF8String
BWAS-Carrier-Identification-Code ::= [210731025] UTF8String
BWAS-Dialed-Digits ::= [210731026] UTF8String
BWAS-Call-Category ::= [210731027] UTF8String
BWAS-Network-Call-Type ::= [210731028] UTF8String
BWAS-Network-Translated-Number ::= [210731029] UTF8String
BWAS-Network-Translated-Group ::= [210731030] UTF8String
BWAS-Releasing-Party ::= [210731031] UTF8String
BWAS-Route ::= [210731032] UTF8String
BWAS-Network-Callid ::= [210731033] UTF8String
BWAS-Codec ::= [210731034] UTF8String
BWAS-Access-Device-Address ::= [210731035] UTF8String
BWAS-Access-Callid ::= [210731036] UTF8String
BWAS-Failover-Correlation-Id ::= [210731038] UTF8String
BWAS-Group ::= [210731040] UTF8String
BWAS-Department ::= [210731041] UTF8String
BWAS-Account-Code ::= [210731042] UTF8String
BWAS-Authorization-Code ::= [210731043] UTF8String
BWAS-Original-Called-Number ::= [210731044] UTF8String
BWAS-Original-Called-Presentation-Indic ::= [210731045] UTF8String
BWAS-Original-Called-Reason ::= [210731046] UTF8String
BWAS-Redirecting-Number ::= [210731047] UTF8String
BWAS-Redirecting-Presentation-Indic ::= [210731048] UTF8String
BWAS-Redirecting-Reason ::= [210731049] UTF8String
BWAS-Charge-Indic ::= [210731050] UTF8String
BWAS-Type-Of-Network ::= [210731051] UTF8String
BWAS-VP-Calling-Invoke-Time ::= [210731052] UTF8String
BWAS-Local-Callid ::= [210731053] UTF8String
BWAS-Remote-Callid ::= [210731054] UTF8String
BWAS-Calling-Party-Category ::= [210731055] UTF8String
BWAS-Charging-Vector-Key ::= [210731067] UTF8String
BWAS-Charging-Vector-Creator ::= [210731068] UTF8String
BWAS-Charging-Vector-Orig ::= [210731069] UTF8String
BWAS-Charging-Vector-Term ::= [210731070] UTF8String
BWAS-Acc-Per-Call-Invoke-Time ::= [210731071] UTF8String
BWAS-Acc-Per-Call-Fac-Result ::= [210731072] UTF8String
BWAS-Acb-Act-Invoke-Time ::= [210731073] UTF8String
BWAS-Acb-Act-Fac-Result ::= [210731074] UTF8String
BWAS-Acb-Deact-Invoke-Time ::= [210731075] UTF8String
BWAS-Acb-Deact-Fac-Result ::= [210731076] UTF8String
BWAS-Call-Park-Invoke-Time ::= [210731077] UTF8String
BWAS-Call-Park-Fac-Result ::= [210731078] UTF8String
BWAS-Call-Park-Retr-Invoke-Time ::= [210731079] UTF8String
BWAS-Call-Park-Retr-Fac-Result ::= [210731080] UTF8String
BWAS-Call-Pickup-Invoke-Time ::= [210731081] UTF8String
BWAS-Call-Pickup-Fac-Result ::= [210731082] UTF8String
BWAS-Directed-Call-Pickup-Invoke-Time ::= [210731083] UTF8String
BWAS-Directed-Call-Pickup-Fac-Result ::= [210731084] UTF8String
BWAS-Dpubi-Invoke-Time ::= [210731085] UTF8String
BWAS-Dpubi-Fac-Result ::= [210731086] UTF8String
BWAS-Cancel-Cwt-Per-Call-Invoke-Time ::= [210731087] UTF8String
BWAS-Cancel-Cwt-Per-Call-Fac-Result ::= [210731088] UTF8String
BWAS-Cfa-Act-Invoke-Time ::= [210731089] UTF8String
BWAS-Cfa-Act-Fac-Result ::= [210731090] UTF8String
BWAS-Cfa-Deact-Invoke-Time ::= [210731091] UTF8String
BWAS-Cfa-Deact-Fac-Result ::= [210731092] UTF8String
BWAS-Cfb-Act-Invoke-Time ::= [210731093] UTF8String
BWAS-Cfb-Act-Fac-Result ::= [210731094] UTF8String
BWAS-Cfb-Deact-Invoke-Time ::= [210731095] UTF8String
BWAS-Cfb-Deact-Fac-Result ::= [210731096] UTF8String
BWAS-Cfna-Act-Invoke-Time ::= [210731097] UTF8String
BWAS-Cfna-Act-Fac-Result ::= [210731098] UTF8String
BWAS-Cfna-Deact-Invoke-Time ::= [210731099] UTF8String
BWAS-Cfna-Deact-Fac-Result ::= [210731100] UTF8String
BWAS-Clid-Delivery-Per-Call-Invoke-Time ::= [210731101] UTF8String
BWAS-Clid-Delivery-Per-Call-Fac-Result ::= [210731102] UTF8String
BWAS-Clid-Blocking-Per-Call-Invoke-Time ::= [210731103] UTF8String
BWAS-Clid-Blocking-Per-Call-Fac-Result ::= [210731104] UTF8String
BWAS-Cot-Invoke-Time ::= [210731105] UTF8String
BWAS-Cot-Fac-Result ::= [210731106] UTF8String
BWAS-Direct-Vm-Xfer-Invoke-Time ::= [210731107] UTF8String
BWAS-Direct-Vm-Xfer-Fac-Result ::= [210731108] UTF8String
BWAS-Dnd-Act-Invoke-Time ::= [210731109] UTF8String
BWAS-Dnd-Act-Fac-Result ::= [210731110] UTF8String
BWAS-Dnd-Deact-Invoke-Time ::= [210731111] UTF8String
BWAS-Dnd-Deact-Fac-Result ::= [210731112] UTF8String
BWAS-Sac-Lock-Invoke-Time ::= [210731113] UTF8String
BWAS-Sac-Lock-Fac-Result ::= [210731114] UTF8String
BWAS-Sac-Unlock-Invoke-Time ::= [210731115] UTF8String
BWAS-Sac-Unlock-Fac-Result ::= [210731116] UTF8String
BWAS-Flash-Call-Hold-Invoke-Time ::= [210731117] UTF8String
BWAS-Flash-Call-Hold-Fac-Result ::= [210731118] UTF8String
BWAS-Last-Number-Redial-Invoke-Time ::= [210731119] UTF8String
BWAS-Last-Number-Redial-Fac-Result ::= [210731120] UTF8String
BWAS-Return-Call-Invoke-Time ::= [210731121] UTF8String
BWAS-Return-Call-Fac-Result ::= [210731122] UTF8String
BWAS-Sd100-Programming-Invoke-Time ::= [210731123] UTF8String
BWAS-Sd100-Programming-Fac-Result ::= [210731124] UTF8String
BWAS-Sd8-Programming-Invoke-Time ::= [210731125] UTF8String
BWAS-Sd8-Programming-Fac-Result ::= [210731126] UTF8String
BWAS-Clear-Mwi-Invoke-Time ::= [210731127] UTF8String
BWAS-Clear-Mwi-Fac-Result ::= [210731128] UTF8String
BWAS-UserId ::= [210731129] UTF8String
BWAS-Other-Party-Name ::= [210731130] UTF8String
BWAS-Other-Party-Name-Pres-Indic ::= [210731131] UTF8String
BWAS-Moh-Deact-Invoke-Time ::= [210731132] UTF8String
BWAS-Moh-Deact-Fac-Result ::= [210731133] UTF8String
BWAS-Push-to-Talk-Invoke-Time ::= [210731134] UTF8String
BWAS-Push-to-Talk-Fac-Result ::= [210731135] UTF8String
BWAS-Hoteling-Invoke-Time ::= [210731136] UTF8String
BWAS-Hoteling-Group ::= [210731137] UTF8String
BWAS-Hoteling-UserId ::= [210731138] UTF8String
BWAS-Hoteling-User-Number ::= [210731139] UTF8String
BWAS-Hoteling-Group-Number ::= [210731140] UTF8String
BWAS-Diversion-Inhibitor-Invoke-time ::= [210731141] UTF8String
BWAS-Diversion-Inhibitor-Fac-Result ::= [210731142] UTF8String
BWAS-Trunk-Group-Name ::= [210731143] UTF8String
BWAS-InstantGroupCall-Invoke-Time ::= [210731145] UTF8String
BWAS-InstantGroupCall-PushToTalk ::= [210731146] UTF8String
BWAS-InstantGroupCall-Related-Callid ::= [210731147] UTF8String
BWAS-CustomRingback-Invoke-Time ::= [210731148] UTF8String
BWAS-CLID-Permitted ::= [210731149] UTF8String
BWAS-AHR-Invoke-Time ::= [210731150] UTF8String
BWAS-AHR-Action ::= [210731151] UTF8String
BWAS-Access-Network-Info ::= [210731152] UTF8String
BWAS-Charging-Function-Addresses ::= [210731153] UTF8String
BWAS-Charge-Number ::= [210731154] UTF8String
BWAS-Related-CallId ::= [210731155] UTF8String
BWAS-Related-CallId-Reason ::= [210731156] UTF8String
BWAS-Transfer-Invoke-Time ::= [210731157] UTF8String
BWAS-Transfer-Result ::= [210731158] UTF8String
BWAS-Transfer-Related-CallId ::= [210731159] UTF8String
BWAS-Transfer-Type ::= [210731160] UTF8String
BWAS-Conf-Start-Time ::= [210731161] UTF8String
BWAS-Conf-Stop-Time ::= [210731162] UTF8String
BWAS-Conf-Id ::= [210731163] UTF8String
BWAS-Conf-Type ::= [210731164] UTF8String
BWAS-Codec-Usage ::= [210731165] UTF8String
BWAS-Vmb-Act-Invoke-Time ::= [210731166] UTF8String
BWAS-Vmb-Act-Fac-Result ::= [210731167] UTF8String
BWAS-Vmb-Deact-Invoke-Time ::= [210731168] UTF8String
BWAS-Vmb-Deact-Fac-Result ::= [210731169] UTF8String
BWAS-Vmna-Act-Invoke-Time ::= [210731170] UTF8String
BWAS-Vmna-Act-Fac-Result ::= [210731171] UTF8String
BWAS-Vmna-Deact-Invoke-Time ::= [210731172] UTF8String
BWAS-Vmna-Deact-Fac-Result ::= [210731173] UTF8String
BWAS-Vma-Act-Invoke-Time ::= [210731174] UTF8String
BWAS-Vma-Act-Fac-Result ::= [210731175] UTF8String
BWAS-Vma-Deact-Invoke-Time ::= [210731176] UTF8String
BWAS-Vma-Deact-Fac-Result ::= [210731177] UTF8String
BWAS-No-Answer-Set-Invoke-Time ::= [210731178] UTF8String
BWAS-No-Answer-Set-Fac-Result ::= [210731179] UTF8String
BWAS-Clid-Blocking-Act-Invoke-Time ::= [210731180] UTF8String
BWAS-Clid-Blocking-Act-Fac-Result ::= [210731181] UTF8String
BWAS-Clid-Blocking-Deact-Invoke-Time ::= [210731182] UTF8String
BWAS-Clid-Blocking-Deact-Fac-Result ::= [210731183] UTF8String
BWAS-Call-Waiting-Act-Invoke-Time ::= [210731184] UTF8String
BWAS-Call-Waiting-Act-Fac-Result ::= [210731185] UTF8String
BWAS-Call-Waiting-Deact-Invoke-Time ::= [210731186] UTF8String
BWAS-Call-Waiting-Deact-Fac-Result ::= [210731187] UTF8String
BWAS-Fax-Messaging ::= [210731188] UTF8String
BWAS-TSD-Digits ::= [210731189] UTF8String
BWAS-Trunk-Group-Info ::= [210731190] UTF8String
BWAS-Recall-Type ::= [210731191] UTF8String
BWAS-Cfnrc-Act-Invoke-Time ::= [210731192] UTF8String
BWAS-Cfnrc-Act-Fac-Result ::= [210731193] UTF8String
BWAS-Cfnrc-Deact-Invoke-Time ::= [210731194] UTF8String
BWAS-Cfnrc-Deact-Fac-Result ::= [210731195] UTF8String
BWAS-Q850-Cause ::= [210731196] UTF8String
BWAS-Dialed-Digits-Context ::= [210731197] UTF8String
BWAS-Called-Number-Context ::= [210731198] UTF8String
BWAS-Network-Translated-Number-Context ::= [210731199] UTF8String
BWAS-Calling-Number-Context ::= [210731200] UTF8String
BWAS-Original-Called-Number-Context ::= [210731201] UTF8String
BWAS-Redirecting-Number-Context ::= [210731202] UTF8String
BWAS-Location-Control-Act-Result ::= [210731203] UTF8String
BWAS-Location-Control-Deact-Result ::= [210731204] UTF8String
BWAS-Call-Retrieve-Result ::= [210731205] UTF8String
BWAS-Routing-Number ::= [210731206] UTF8String
BWAS-Origination-Method ::= [210731207] UTF8String
BWAS-Call-Parked-Invoke-Time ::= [210731208] UTF8String
BWAS-BA-Related-Call-Id ::= [210731209] UTF8String
BWAS-Acr-Act-Invoke-Time ::= [210731210] UTF8String
BWAS-Acr-Act-Fac-Result ::= [210731211] UTF8String
BWAS-Acr-Deact-Invoke-Time ::= [210731212] UTF8String
BWAS-Acr-Deact-Fac-Result ::= [210731213] UTF8String
BWAS-Outside-Access-Code ::= [210731214] UTF8String
BWAS-Primary-Device-Line-Port ::= [210731215] UTF8String
BWAS-Called-Asserted-Identity ::= [210731216] UTF8String
BWAS-Called-Asserted-Pres-Indicator ::= [210731217] UTF8String
BWAS-SDP ::= [210731218] UTF8String
BWAS-Media-Initiator-Flag ::= [210731219] UTF8String
BWAS-SDP-Offer-Timestamp ::= [210731220] UTF8String
BWAS-SDP-Answer-Timestamp ::= [210731221] UTF8String
BWAS-Early-Media-SDP ::= [210731222] UTF8String
BWAS-Early-Media-Initiator-Flag ::= [210731223] UTF8String
BWAS-Body-Content-Type ::= [210731224] UTF8String
BWAS-Body-Content-Length ::= [210731225] UTF8String
BWAS-Body-Content-Disposition ::= [210731226] UTF8String
BWAS-Body-Originator ::= [210731227] UTF8String
BWAS-SIP-Error-Code ::= [210731228] UTF8String
BWAS-otherInfoInPCV ::= [210731229] UTF8String
BWAS-Received-Calling-Number ::= [210731230] UTF8String
BWAS-CustomRingback-Media-Selection ::= [210731231] UTF8String
BWAS-AOC-Type ::= [210731232] UTF8String
BWAS-AOC-Charge ::= [210731233] UTF8String
BWAS-AOC-Currency ::= [210731234] UTF8String
BWAS-AOC-Time ::= [210731235] UTF8String
BWAS-AOC-Sum ::= [210731236] UTF8String
BWAS-AOC-Activation-Time ::= [210731237] UTF8String
BWAS-AOC-Result ::= [210731238] UTF8String
BWAS-AS-Call-Type ::= [210731239] UTF8String
BWAS-Scf-Act-Invoke-Time ::= [210731240] UTF8String
BWAS-Scf-Act-Fac-Result ::= [210731241] UTF8String
BWAS-Scf-Deact-Invoke-Time ::= [210731242] UTF8String
BWAS-Scf-Deact-Fac-Result ::= [210731243] UTF8String
BWAS-Cfa-Inter-Invoke-Time ::= [210731244] UTF8String
BWAS-Cfa-Inter-Fac-Result ::= [210731245] UTF8String
BWAS-Cfna-Inter-Invoke-Time ::= [210731246] UTF8String
BWAS-Cfna-Inter-Fac-Result ::= [210731247] UTF8String
BWAS-Cfb-Inter-Invoke-Time ::= [210731248] UTF8String
BWAS-Cfb-Inter-Fac-Result ::= [210731249] UTF8String
BWAS-CBF-Auth-Code ::= [210731250] UTF8String
BWAS-Call-Bridge-Result ::= [210731251] UTF8String
BWAS-Return-Call-Number-Deletion-Invoke-Time ::= [210731252] UTF8String
BWAS-Return-Call-Number-Deletion-Fac-Result ::= [210731253] UTF8String
BWAS-Prepaid-Status ::= [210731254] UTF8String
BWAS-Configurable-CLID ::= [210731255] UTF8String
BWAS-Call-Center-Night-Service-Act-Result ::= [210731256] UTF8String
BWAS-Call-Center-Night-Service-Deact-Result ::= [210731257] UTF8String
BWAS-Call-Center-Forced-Forwarding-Act-Result ::= [210731258] UTF8String
BWAS-Call-Center-Forced-Forwarding-Deact-Result ::= [210731259] UTF8String
BWAS-Call-Center-Outgoing-Call-FAC-Result ::= [210731260] UTF8String
BWAS-Call-Center-Outgoing-Personal-Call-FAC-Result ::= [210731261] UTF8String
BWAS-Call-Center-Outgoing-Phone-Number ::= [210731262] UTF8String
BWAS-Intercept-User-Routing-Number ::= [210731263] UTF8String
BWAS-Intercept-Group-Routing-Number ::= [210731264] UTF8String
BWAS-CB-Activation-Invoke-Time ::= [210731265] UTF8String
BWAS-CB-Activation-Fac-Result ::= [210731266] UTF8String
BWAS-CB-Deactivation-Invoke-Time ::= [210731267] UTF8String
BWAS-CB-Deactivation-Fac-Result ::= [210731268] UTF8String
BWAS-CB-Query-Invoke-Time ::= [210731269] UTF8String
BWAS-CB-Query-Fac-Result ::= [210731270] UTF8String
BWAS-Cfnrc-Inter-Invoke-Time ::= [210731271] UTF8String
BWAS-Cfnrc-Inter-Fac-Result ::= [210731272] UTF8String
BWAS-VMR-Dialing-Invoke-Time ::= [210731273] UTF8String
BWAS-VMR-Dialing-Fac-result ::= [210731274] UTF8String
BWAS-VP-Dialing-Invoke-Time ::= [210731275] UTF8String
BWAS-VP-Dialing-Fac-result ::= [210731276] UTF8String
BWAS-Camel-Loc-Info ::= [210731277] UTF8String
BWAS-Camel-Msc-Address ::= [210731278] UTF8String
BWAS-Camel-CellId-Or-LAI ::= [210731279] UTF8String
BWAS-NAME-Permitted ::= [210731280] UTF8String
BWAS-Call-Center-User-Id ::= [210731281] UTF8String
BWAS-Call-Center-Outgoing-Group-Phone-Number ::= [210731282] UTF8String
BWAS-VON-Type ::= [210731283] UTF8String
BWAS-PreAlertingAnncmtDuration ::= [210731284] UTF8String
BWAS-CC-Disp-Code-Tagging-Invoke-Time ::= [210731285] UTF8String
BWAS-CC-Disp-Code-Tagging-Result ::= [210731286] UTF8String
BWAS-CC-Escalated-Call-Invoke-Time ::= [210731287] UTF8String
BWAS-CC-Escalated-Call-FAC-Result ::= [210731288] UTF8String
BWAS-CC-Monitoring-BI-Invoke-Time ::= [210731289] UTF8String
BWAS-CC-Monitoring-BI-FAC-Result ::= [210731290] UTF8String
BWAS-Mid-Call-Cot-Invoke-Time ::= [210731291] UTF8String
BWAS-Office-Zone ::= [210731292] UTF8String
BWAS-Primary-Zone ::= [210731293] UTF8String
BWAS-Roaming-MSC-Address ::= [210731294] UTF8String
BWAS-CC-Emergency-Call-Invoke-Time ::= [210731295] UTF8String
BWAS-Monitoring-Next-Call-Invoke-Time ::= [210731296] UTF8String
BWAS-Monitoring-Next-Call-FAC-Result ::= [210731297] UTF8String
BWAS-Legacy-Acb-Act-Invoke-Time ::= [210731298] UTF8String
BWAS-Legacy-Acb-Act-Fac-Result ::= [210731299] UTF8String
BWAS-Legacy-Acb-Deact-Invoke-Time ::= [210731300] UTF8String
BWAS-Legacy-Acb-Deact-Fac-Result ::= [210731301] UTF8String
BWAS-Custom-Schema-Version ::= [210731302] UTF8String
BWAS-Group-Paging-Invoke-Time ::= [210731303] UTF8String
BWAS-Group-Paging-Related-CallId ::= [210731304] UTF8String
BWAS-DCLID ::= [210731305] UTF8String
BWAS-MeetMeConferencing-InvokeTime ::= [210731306] UTF8String
BWAS-Call-Me-Now-Type ::= [210731307] UTF8String
BWAS-Call-Me-Now-Transaction-Id ::= [210731308] UTF8String
BWAS-Call-Me-Now-Related-Call-Id ::= [210731309] UTF8String
BWAS-MeetMeConferencing-ConferenceId ::= [210731310] UTF8String
BWAS-MeetMeConferencing-Role ::= [210731311] UTF8String
BWAS-MeetMeConferencing-Bridge ::= [210731312] UTF8String
BWAS-MeetMeConferencing-Owner ::= [210731313] UTF8String
BWAS-MeetMeConferencing-OwnerDn ::= [210731314] UTF8String
BWAS-MeetMeConferencing-Title ::= [210731315] UTF8String
BWAS-MeetMeConferencing-ProjectCode ::= [210731316] UTF8String
BWAS-MeetMeConferencing-RecordDuration ::= [210731317] UTF8String
BWAS-MobilityNumber ::= [210731318] UTF8String
BWAS-MobilityRoutingNumber ::= [210731319] UTF8String
BWAS-Location ::= [210731320] UTF8String
BWAS-Location-Type ::= [210731321] UTF8String
BWAS-Location-Usage ::= [210731322] UTF8String
BWAS-Call-Recording-Invocation-Time ::= [210731323] UTF8String
BWAS-Call-Recording-FAC-Result ::= [210731324] UTF8String
BWAS-Call-Recording-Trigger ::= [210731325] UTF8String
BWAS-Call-Recording-Destination ::= [210731326] UTF8String
BWAS-Call-Recording-Result ::= [210731327] UTF8String
BWAS-Calling-Pres-Number ::= [210731328] UTF8String
BWAS-Calling-Pres-Number-Context ::= [210731329] UTF8String
BWAS-Calling-Asserted-Number ::= [210731330] UTF8String
BWAS-Calling-Asserted-Number-Context ::= [210731331] UTF8String
BWAS-SCC-Invocation-Time ::= [210731332] UTF8String
BWAS-SCC-Call-Id ::= [210731333] UTF8String
BWAS-SCC-Number ::= [210731334] UTF8String
BWAS-Acr-Inter-Invoke-Time ::= [210731335] UTF8String
BWAS-Acr-Inter-Fac-Result ::= [210731336] UTF8String
BWAS-CW-Inter-Invoke-Time ::= [210731337] UTF8String
BWAS-CW-Inter-Fac-Result ::= [210731338] UTF8String
BWAS-Clid-Blocking-Inter-Invoke-Time ::= [210731339] UTF8String
BWAS-Clid-Blocking-Inter-Fac-Result ::= [210731340] UTF8String
BWAS-Colr-Inter-Invoke-Time ::= [210731341] UTF8String
BWAS-Colr-Inter-Fac-Result ::= [210731342] UTF8String
BWAS-Scr-Inter-Invoke-Time ::= [210731343] UTF8String
BWAS-Scr-Inter-Fac-Result ::= [210731344] UTF8String
BWAS-User-Agent ::= [210731354] UTF8String
BWAS-FMFM-Call-Push-Invocation-Time ::= [210731355] UTF8String
BWAS-FMFM-Call-Push-FAC-Result ::= [210731356] UTF8String
END
