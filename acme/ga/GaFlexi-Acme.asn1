GaFlexi-Acme DEFINITIONS IMPLICIT TAGS ::= BEGIN

Address32 ::= OCTET STRING
Address128 ::= OCTET STRING

Request ::= SEQUENCE {
	user-Name User-Name OPTIONAL,
	user-Password User-Password OPTIONAL,
	cHAP-Password CHAP-Password OPTIONAL,
	nAS-IP-Address NAS-IP-Address OPTIONAL,
	nAS-Port NAS-Port OPTIONAL,
	service-Type Service-Type OPTIONAL,
	framed-Protocol Framed-Protocol OPTIONAL,
	framed-IP-Address Framed-IP-Address OPTIONAL,
	framed-IP-Netmask Framed-IP-Netmask OPTIONAL,
	framed-Routing Framed-Routing OPTIONAL,
	filter-Id Filter-Id OPTIONAL,
	framed-MTU Framed-MTU OPTIONAL,
	framed-Compression Framed-Compression OPTIONAL,
	login-IP-Host Login-IP-Host OPTIONAL,
	login-Service Login-Service OPTIONAL,
	login-TCP-Port Login-TCP-Port OPTIONAL,
	reply-Message Reply-Message OPTIONAL,
	callback-Number Callback-Number OPTIONAL,
	callback-Id Callback-Id OPTIONAL,
	framed-Route Framed-Route OPTIONAL,
	framed-IPX-Network Framed-IPX-Network OPTIONAL,
	state State OPTIONAL,
	class Class OPTIONAL,
	session-Timeout Session-Timeout OPTIONAL,
	idle-Timeout Idle-Timeout OPTIONAL,
	termination-Action Termination-Action OPTIONAL,
	called-Station-Id Called-Station-Id OPTIONAL,
	calling-Station-Id Calling-Station-Id OPTIONAL,
	nAS-Identifier NAS-Identifier OPTIONAL,
	proxy-State Proxy-State OPTIONAL,
	login-LAT-Service Login-LAT-Service OPTIONAL,
	login-LAT-Node Login-LAT-Node OPTIONAL,
	login-LAT-Group Login-LAT-Group OPTIONAL,
	framed-AppleTalk-Link Framed-AppleTalk-Link OPTIONAL,
	framed-AppleTalk-Network Framed-AppleTalk-Network OPTIONAL,
	framed-AppleTalk-Zone Framed-AppleTalk-Zone OPTIONAL,
	cHAP-Challenge CHAP-Challenge OPTIONAL,
	nAS-Port-Type NAS-Port-Type OPTIONAL,
	port-Limit Port-Limit OPTIONAL,
	login-LAT-Port Login-LAT-Port OPTIONAL,
	acct-Status-Type Acct-Status-Type OPTIONAL,
	acct-Delay-Time Acct-Delay-Time OPTIONAL,
	acct-Input-Octets Acct-Input-Octets OPTIONAL,
	acct-Output-Octets Acct-Output-Octets OPTIONAL,
	acct-Session-Id Acct-Session-Id OPTIONAL,
	acct-Authentic Acct-Authentic OPTIONAL,
	acct-Session-Time Acct-Session-Time OPTIONAL,
	acct-Input-Packets Acct-Input-Packets OPTIONAL,
	acct-Output-Packets Acct-Output-Packets OPTIONAL,
	acct-Terminate-Cause Acct-Terminate-Cause OPTIONAL,
	acct-Multi-Session-Id Acct-Multi-Session-Id OPTIONAL,
	acct-Link-Count Acct-Link-Count OPTIONAL,
	acct-Input-Gigawords Acct-Input-Gigawords OPTIONAL,
	acct-Output-Gigawords Acct-Output-Gigawords OPTIONAL,
	event-Timestamp Event-Timestamp OPTIONAL,
	aRAP-Password ARAP-Password OPTIONAL,
	aRAP-Features ARAP-Features OPTIONAL,
	aRAP-Zone-Access ARAP-Zone-Access OPTIONAL,
	aRAP-Security ARAP-Security OPTIONAL,
	aRAP-Security-Data ARAP-Security-Data OPTIONAL,
	password-Retry Password-Retry OPTIONAL,
	prompt Prompt OPTIONAL,
	connect-Info Connect-Info OPTIONAL,
	configuration-Token Configuration-Token OPTIONAL,
	eAP-Message EAP-Message OPTIONAL,
	message-Authenticator Message-Authenticator OPTIONAL,
	aRAP-Challenge-Response ARAP-Challenge-Response OPTIONAL,
	acct-Interim-Interval Acct-Interim-Interval OPTIONAL,
	nAS-Port-Id NAS-Port-Id OPTIONAL,
	framed-Pool Framed-Pool OPTIONAL,
	setupTime SetupTime OPTIONAL,
	connectTime ConnectTime OPTIONAL,
	disconnectTime DisconnectTime OPTIONAL,
	disconnectCause DisconnectCause OPTIONAL,
	acme-FlowID-FS1-F Acme-FlowID-FS1-F OPTIONAL,
	acme-FlowType-FS1-F Acme-FlowType-FS1-F OPTIONAL,
	acme-Session-Ingress-CallId Acme-Session-Ingress-CallId OPTIONAL,
	acme-Session-Egress-CallId Acme-Session-Egress-CallId OPTIONAL,
	acme-Flow-In-Realm-FS1-F Acme-Flow-In-Realm-FS1-F OPTIONAL,
	acme-Flow-In-Src-Addr-FS1-F Acme-Flow-In-Src-Addr-FS1-F OPTIONAL,
	acme-Flow-In-Src-Port-FS1-F Acme-Flow-In-Src-Port-FS1-F OPTIONAL,
	acme-Flow-In-Dst-Addr-FS1-F Acme-Flow-In-Dst-Addr-FS1-F OPTIONAL,
	acme-Flow-In-Dst-Port-FS1-F Acme-Flow-In-Dst-Port-FS1-F OPTIONAL,
	acme-Flow-Out-Realm-FS1-F Acme-Flow-Out-Realm-FS1-F OPTIONAL,
	acme-Flow-Out-Src-Addr-FS1-F Acme-Flow-Out-Src-Addr-FS1-F OPTIONAL,
	acme-Flow-Out-Src-Port-FS1-F Acme-Flow-Out-Src-Port-FS1-F OPTIONAL,
	acme-Flow-Out-Dst-Addr-FS1-F Acme-Flow-Out-Dst-Addr-FS1-F OPTIONAL,
	acme-Flow-Out-Dst-Port-FS1-F Acme-Flow-Out-Dst-Port-FS1-F OPTIONAL,
	acme-Calling-Octets-FS1 Acme-Calling-Octets-FS1 OPTIONAL,
	acme-Calling-Packets-FS1 Acme-Calling-Packets-FS1 OPTIONAL,
	acme-Calling-RTCP-Packets-Lost-FS1 Acme-Calling-RTCP-Packets-Lost-FS1 OPTIONAL,
	acme-Calling-RTCP-Avg-Jitter-FS1 Acme-Calling-RTCP-Avg-Jitter-FS1 OPTIONAL,
	acme-Calling-RTCP-Avg-Latency-FS1 Acme-Calling-RTCP-Avg-Latency-FS1 OPTIONAL,
	acme-Calling-RTCP-MaxJitter-FS1 Acme-Calling-RTCP-MaxJitter-FS1 OPTIONAL,
	acme-Calling-RTCP-MaxLatency-FS1 Acme-Calling-RTCP-MaxLatency-FS1 OPTIONAL,
	acme-Calling-RTP-Packets-Lost-FS1 Acme-Calling-RTP-Packets-Lost-FS1 OPTIONAL,
	acme-Calling-RTP-Avg-Jitter-FS1 Acme-Calling-RTP-Avg-Jitter-FS1 OPTIONAL,
	acme-Calling-RTP-MaxJitter-FS1 Acme-Calling-RTP-MaxJitter-FS1 OPTIONAL,
	acme-Session-Generic-Id Acme-Session-Generic-Id OPTIONAL,
	acme-Session-Ingress-Realm Acme-Session-Ingress-Realm OPTIONAL,
	acme-Session-Egress-Realm Acme-Session-Egress-Realm OPTIONAL,
	acme-Session-Protocol-Type Acme-Session-Protocol-Type OPTIONAL,
	acme-Called-Octets-FS1 Acme-Called-Octets-FS1 OPTIONAL,
	acme-Called-Packets-FS1 Acme-Called-Packets-FS1 OPTIONAL,
	acme-Called-RTCP-Packets-Lost-FS1 Acme-Called-RTCP-Packets-Lost-FS1 OPTIONAL,
	acme-Called-RTCP-Avg-Jitter-FS1 Acme-Called-RTCP-Avg-Jitter-FS1 OPTIONAL,
	acme-Called-RTCP-Avg-Latency-FS1 Acme-Called-RTCP-Avg-Latency-FS1 OPTIONAL,
	acme-Called-RTCP-MaxJitter-FS1 Acme-Called-RTCP-MaxJitter-FS1 OPTIONAL,
	acme-Called-RTCP-MaxLatency-FS1 Acme-Called-RTCP-MaxLatency-FS1 OPTIONAL,
	acme-Called-RTP-Packets-Lost-FS1 Acme-Called-RTP-Packets-Lost-FS1 OPTIONAL,
	acme-Called-RTP-Avg-Jitter-FS1 Acme-Called-RTP-Avg-Jitter-FS1 OPTIONAL,
	acme-Called-RTP-MaxJitter-FS1 Acme-Called-RTP-MaxJitter-FS1 OPTIONAL,
	acme-Session-Charging-Vector Acme-Session-Charging-Vector OPTIONAL,
	acme-Session-Charging-Function-Address Acme-Session-Charging-Function-Address OPTIONAL,
	acme-Firmware-Version Acme-Firmware-Version OPTIONAL,
	acme-Local-Time-Zone Acme-Local-Time-Zone OPTIONAL,
	acme-Post-Dial-Delay Acme-Post-Dial-Delay OPTIONAL,
	acme-CDR-Sequence-Number Acme-CDR-Sequence-Number OPTIONAL,
	acme-Session-Disposition Acme-Session-Disposition OPTIONAL,
	acme-Disconnect-Initiator Acme-Disconnect-Initiator OPTIONAL,
	acme-Disconnect-Cause Acme-Disconnect-Cause OPTIONAL,
	acme-Intermediate-Time Acme-Intermediate-Time OPTIONAL,
	acme-Primary-Routing-Number Acme-Primary-Routing-Number OPTIONAL,
	acme-Originating-Trunk-Group Acme-Originating-Trunk-Group OPTIONAL,
	acme-Terminating-Trunk-Group Acme-Terminating-Trunk-Group OPTIONAL,
	acme-Originating-Trunk-Context Acme-Originating-Trunk-Context OPTIONAL,
	acme-Terminating-Trunk-Context Acme-Terminating-Trunk-Context OPTIONAL,
	acme-P-Asserted-ID Acme-P-Asserted-ID OPTIONAL,
	acme-SIP-Diversion Acme-SIP-Diversion OPTIONAL,
	acme-SIP-Status Acme-SIP-Status OPTIONAL,
	acme-Ingress-Local-Addr Acme-Ingress-Local-Addr OPTIONAL,
	acme-Ingress-Remote-Addr Acme-Ingress-Remote-Addr OPTIONAL,
	acme-Egress-Local-Addr Acme-Egress-Local-Addr OPTIONAL,
	acme-Egress-Remote-Addr Acme-Egress-Remote-Addr OPTIONAL,
	acme-FlowID-FS1-R Acme-FlowID-FS1-R OPTIONAL,
	acme-FlowType-FS1-R Acme-FlowType-FS1-R OPTIONAL,
	acme-Flow-In-Realm-FS1-R Acme-Flow-In-Realm-FS1-R OPTIONAL,
	acme-Flow-In-Src-Addr-FS1-R Acme-Flow-In-Src-Addr-FS1-R OPTIONAL,
	acme-Flow-In-Src-Port-FS1-R Acme-Flow-In-Src-Port-FS1-R OPTIONAL,
	acme-Flow-In-Dst-Addr-FS1-R Acme-Flow-In-Dst-Addr-FS1-R OPTIONAL,
	acme-Flow-In-Dst-Port-FS1-R Acme-Flow-In-Dst-Port-FS1-R OPTIONAL,
	acme-Flow-Out-Realm-FS1-R Acme-Flow-Out-Realm-FS1-R OPTIONAL,
	acme-Flow-Out-Src-Addr-FS1-R Acme-Flow-Out-Src-Addr-FS1-R OPTIONAL,
	acme-Flow-Out-Src-Port-FS1-R Acme-Flow-Out-Src-Port-FS1-R OPTIONAL,
	acme-Flow-Out-Dst-Addr-FS1-R Acme-Flow-Out-Dst-Addr-FS1-R OPTIONAL,
	acme-Flow-Out-Dst-Port-FS1-R Acme-Flow-Out-Dst-Port-FS1-R OPTIONAL,
	acme-FlowID-FS2-F Acme-FlowID-FS2-F OPTIONAL,
	acme-FlowType-FS2-F Acme-FlowType-FS2-F OPTIONAL,
	acme-Flow-In-Realm-FS2-F Acme-Flow-In-Realm-FS2-F OPTIONAL,
	acme-Flow-In-Src-Addr-FS2-F Acme-Flow-In-Src-Addr-FS2-F OPTIONAL,
	acme-Flow-In-Src-Port-FS2-F Acme-Flow-In-Src-Port-FS2-F OPTIONAL,
	acme-Flow-In-Dst-Addr-FS2-F Acme-Flow-In-Dst-Addr-FS2-F OPTIONAL,
	acme-Flow-In-Dst-Port-FS2-F Acme-Flow-In-Dst-Port-FS2-F OPTIONAL,
	acme-Flow-Out-Realm-FS2-F Acme-Flow-Out-Realm-FS2-F OPTIONAL,
	acme-Flow-Out-Src-Addr-FS2-F Acme-Flow-Out-Src-Addr-FS2-F OPTIONAL,
	acme-Flow-Out-Src-Port-FS2-F Acme-Flow-Out-Src-Port-FS2-F OPTIONAL,
	acme-Flow-Out-Dst-Addr-FS2-F Acme-Flow-Out-Dst-Addr-FS2-F OPTIONAL,
	acme-Flow-Out-Dst-Port-FS2-F Acme-Flow-Out-Dst-Port-FS2-F OPTIONAL,
	acme-Calling-Octets-FS2 Acme-Calling-Octets-FS2 OPTIONAL,
	acme-Calling-Packets-FS2 Acme-Calling-Packets-FS2 OPTIONAL,
	acme-Calling-RTCP-Packets-Lost-FS2 Acme-Calling-RTCP-Packets-Lost-FS2 OPTIONAL,
	acme-Calling-RTCP-Avg-Jitter-FS2 Acme-Calling-RTCP-Avg-Jitter-FS2 OPTIONAL,
	acme-Calling-RTCP-Avg-Latency-FS2 Acme-Calling-RTCP-Avg-Latency-FS2 OPTIONAL,
	acme-Calling-RTCP-MaxJitter-FS2 Acme-Calling-RTCP-MaxJitter-FS2 OPTIONAL,
	acme-Calling-RTCP-MaxLatency-FS2 Acme-Calling-RTCP-MaxLatency-FS2 OPTIONAL,
	acme-Calling-RTP-Packets-Lost-FS2 Acme-Calling-RTP-Packets-Lost-FS2 OPTIONAL,
	acme-Calling-RTP-Avg-Jitter-FS2 Acme-Calling-RTP-Avg-Jitter-FS2 OPTIONAL,
	acme-Calling-RTP-MaxJitter-FS2 Acme-Calling-RTP-MaxJitter-FS2 OPTIONAL,
	acme-FlowID-FS2-R Acme-FlowID-FS2-R OPTIONAL,
	acme-FlowType-FS2-R Acme-FlowType-FS2-R OPTIONAL,
	acme-Flow-In-Realm-FS2-R Acme-Flow-In-Realm-FS2-R OPTIONAL,
	acme-Flow-In-Src-Addr-FS2-R Acme-Flow-In-Src-Addr-FS2-R OPTIONAL,
	acme-Flow-In-Src-Port-FS2-R Acme-Flow-In-Src-Port-FS2-R OPTIONAL,
	acme-Flow-In-Dst-Addr-FS2-R Acme-Flow-In-Dst-Addr-FS2-R OPTIONAL,
	acme-Flow-In-Dst-Port-FS2-R Acme-Flow-In-Dst-Port-FS2-R OPTIONAL,
	acme-Flow-Out-Realm-FS2-R Acme-Flow-Out-Realm-FS2-R OPTIONAL,
	acme-Flow-Out-Src-Addr-FS2-R Acme-Flow-Out-Src-Addr-FS2-R OPTIONAL,
	acme-Flow-Out-Src-Port-FS2-R Acme-Flow-Out-Src-Port-FS2-R OPTIONAL,
	acme-Flow-Out-Dst-Addr-FS2-R Acme-Flow-Out-Dst-Addr-FS2-R OPTIONAL,
	acme-Flow-Out-Dst-Port-FS2-R Acme-Flow-Out-Dst-Port-FS2-R OPTIONAL,
	acme-Called-Octets-FS2 Acme-Called-Octets-FS2 OPTIONAL,
	acme-Called-Packets-FS2 Acme-Called-Packets-FS2 OPTIONAL,
	acme-Called-RTCP-Packets-Lost-FS2 Acme-Called-RTCP-Packets-Lost-FS2 OPTIONAL,
	acme-Called-RTCP-Avg-Jitter-FS2 Acme-Called-RTCP-Avg-Jitter-FS2 OPTIONAL,
	acme-Called-RTCP-Avg-Latency-FS2 Acme-Called-RTCP-Avg-Latency-FS2 OPTIONAL,
	acme-Called-RTCP-MaxJitter-FS2 Acme-Called-RTCP-MaxJitter-FS2 OPTIONAL,
	acme-Called-RTCP-MaxLatency-FS2 Acme-Called-RTCP-MaxLatency-FS2 OPTIONAL,
	acme-Called-RTP-Packets-Lost-FS2 Acme-Called-RTP-Packets-Lost-FS2 OPTIONAL,
	acme-Called-RTP-Avg-Jitter-FS2 Acme-Called-RTP-Avg-Jitter-FS2 OPTIONAL,
	acme-Called-RTP-MaxJitter-FS2 Acme-Called-RTP-MaxJitter-FS2 OPTIONAL,
	acme-Egress-Final-Routing-Number Acme-Egress-Final-Routing-Number OPTIONAL,
	acme-Session-Ingress-RPH Acme-Session-Ingress-RPH OPTIONAL,
	acme-Session-Egress-RPH Acme-Session-Egress-RPH OPTIONAL,
	acme-Ingress-Network-Interface-Id Acme-Ingress-Network-Interface-Id OPTIONAL,
	acme-Ingress-Vlan-Tag-Value Acme-Ingress-Vlan-Tag-Value OPTIONAL,
	acme-Egress-Network-Interface-Id Acme-Egress-Network-Interface-Id OPTIONAL,
	acme-Egress-Vlan-Tag-Value Acme-Egress-Vlan-Tag-Value OPTIONAL,
	acme-Refer-Call-Transfer-Id Acme-Refer-Call-Transfer-Id OPTIONAL,
	acme-Calling-R-Factor Acme-Calling-R-Factor OPTIONAL,
	acme-Calling-MOS Acme-Calling-MOS OPTIONAL,
	acme-Called-R-Factor Acme-Called-R-Factor OPTIONAL,
	acme-Called-MOS Acme-Called-MOS OPTIONAL,
	acme-Flow-In-Src-IPv6-Addr-FS1-F Acme-Flow-In-Src-IPv6-Addr-FS1-F OPTIONAL,
	acme-Flow-In-Dst-IPv6-Addr-FS1-F Acme-Flow-In-Dst-IPv6-Addr-FS1-F OPTIONAL,
	acme-Flow-Out-Src-IPv6-Addr-FS1-F Acme-Flow-Out-Src-IPv6-Addr-FS1-F OPTIONAL,
	acme-Flow-Out-Dst-IPv6-Addr-FS1-F Acme-Flow-Out-Dst-IPv6-Addr-FS1-F OPTIONAL,
	acme-Flow-In-Src-IPv6-Addr-FS1-R Acme-Flow-In-Src-IPv6-Addr-FS1-R OPTIONAL,
	acme-Flow-In-Dst-IPv6-Addr-FS1-R Acme-Flow-In-Dst-IPv6-Addr-FS1-R OPTIONAL,
	acme-Flow-Out-Src-IPv6-Addr-FS1-R Acme-Flow-Out-Src-IPv6-Addr-FS1-R OPTIONAL,
	acme-Flow-Out-Dst-IPv6-Addr-FS1-R Acme-Flow-Out-Dst-IPv6-Addr-FS1-R OPTIONAL,
	acme-Flow-In-Src-IPv6-Addr-FS2-F Acme-Flow-In-Src-IPv6-Addr-FS2-F OPTIONAL,
	acme-Flow-In-Dst-IPv6-Addr-FS2-F Acme-Flow-In-Dst-IPv6-Addr-FS2-F OPTIONAL,
	acme-Flow-Out-Src-IPv6-Addr-FS2-F Acme-Flow-Out-Src-IPv6-Addr-FS2-F OPTIONAL,
	acme-Flow-Out-Dst-IPv6-Addr-FS2-F Acme-Flow-Out-Dst-IPv6-Addr-FS2-F OPTIONAL,
	acme-Flow-In-Src-IPv6-Addr-FS2-R Acme-Flow-In-Src-IPv6-Addr-FS2-R OPTIONAL,
	acme-Flow-In-Dst-IPv6-Addr-FS2-R Acme-Flow-In-Dst-IPv6-Addr-FS2-R OPTIONAL,
	acme-Flow-Out-Src-IPv6-Addr-FS2-R Acme-Flow-Out-Src-IPv6-Addr-FS2-R OPTIONAL,
	acme-Flow-Out-Dst-IPv6-Addr-FS2-R Acme-Flow-Out-Dst-IPv6-Addr-FS2-R OPTIONAL,
	acme-Session-Forked-Call-Id Acme-Session-Forked-Call-Id OPTIONAL,
	acme-Custom-VSA-200 Acme-Custom-VSA-200 OPTIONAL,
	acme-Custom-VSA-201 Acme-Custom-VSA-201 OPTIONAL,
	acme-Custom-VSA-202 Acme-Custom-VSA-202 OPTIONAL,
	acme-Custom-VSA-203 Acme-Custom-VSA-203 OPTIONAL,
	acme-Custom-VSA-204 Acme-Custom-VSA-204 OPTIONAL,
	acme-Custom-VSA-205 Acme-Custom-VSA-205 OPTIONAL,
	acme-Custom-VSA-206 Acme-Custom-VSA-206 OPTIONAL,
	acme-Custom-VSA-207 Acme-Custom-VSA-207 OPTIONAL,
	acme-Custom-VSA-208 Acme-Custom-VSA-208 OPTIONAL,
	acme-Custom-VSA-209 Acme-Custom-VSA-209 OPTIONAL,
	acme-Custom-VSA-210 Acme-Custom-VSA-210 OPTIONAL,
	acme-Custom-VSA-211 Acme-Custom-VSA-211 OPTIONAL,
	acme-Custom-VSA-212 Acme-Custom-VSA-212 OPTIONAL,
	acme-Custom-VSA-213 Acme-Custom-VSA-213 OPTIONAL,
	acme-Custom-VSA-214 Acme-Custom-VSA-214 OPTIONAL,
	acme-Custom-VSA-215 Acme-Custom-VSA-215 OPTIONAL,
	acme-Custom-VSA-216 Acme-Custom-VSA-216 OPTIONAL,
	acme-Custom-VSA-217 Acme-Custom-VSA-217 OPTIONAL,
	acme-Custom-VSA-218 Acme-Custom-VSA-218 OPTIONAL,
	acme-Custom-VSA-219 Acme-Custom-VSA-219 OPTIONAL,
	acme-Custom-VSA-220 Acme-Custom-VSA-220 OPTIONAL,
	acme-Custom-VSA-221 Acme-Custom-VSA-221 OPTIONAL,
	acme-Custom-VSA-222 Acme-Custom-VSA-222 OPTIONAL,
	acme-Custom-VSA-223 Acme-Custom-VSA-223 OPTIONAL,
	acme-Custom-VSA-224 Acme-Custom-VSA-224 OPTIONAL,
	acme-Custom-VSA-225 Acme-Custom-VSA-225 OPTIONAL,
	acme-Custom-VSA-226 Acme-Custom-VSA-226 OPTIONAL,
	acme-Custom-VSA-227 Acme-Custom-VSA-227 OPTIONAL,
	acme-Custom-VSA-228 Acme-Custom-VSA-228 OPTIONAL,
	acme-Custom-VSA-229 Acme-Custom-VSA-229 OPTIONAL,
	acme-Custom-VSA-230 Acme-Custom-VSA-230 OPTIONAL,
	acme-Flow-Calling-Media-Stop-Time-FS1 Acme-Flow-Calling-Media-Stop-Time-FS1 OPTIONAL,
	acme-Flow-Called-Media-Stop-Time-FS1 Acme-Flow-Called-Media-Stop-Time-FS1 OPTIONAL,
	acme-Flow-Calling-Media-Stop-Time-FS2 Acme-Flow-Calling-Media-Stop-Time-FS2 OPTIONAL,
	acme-Flow-Called-Media-Stop-Time-FS2 Acme-Flow-Called-Media-Stop-Time-FS2 OPTIONAL,
	acme-User-Class Acme-User-Class OPTIONAL
}
User-Name ::= [1] UTF8String
User-Password ::= [2] UTF8String
CHAP-Password ::= [3] UTF8String
NAS-IP-Address ::= [4] Address32
NAS-Port ::= [5] INTEGER
Service-Type ::= [6] INTEGER
Framed-Protocol ::= [7] INTEGER
Framed-IP-Address ::= [8] Address32
Framed-IP-Netmask ::= [9] Address32
Framed-Routing ::= [10] INTEGER
Filter-Id ::= [11] UTF8String
Framed-MTU ::= [12] INTEGER
Framed-Compression ::= [13] INTEGER
Login-IP-Host ::= [14] Address32
Login-Service ::= [15] INTEGER
Login-TCP-Port ::= [16] INTEGER
Reply-Message ::= [18] UTF8String
Callback-Number ::= [19] UTF8String
Callback-Id ::= [20] UTF8String
Framed-Route ::= [22] UTF8String
Framed-IPX-Network ::= [23] INTEGER
State ::= [24] UTF8String
Class ::= [25] UTF8String
Session-Timeout ::= [27] INTEGER
Idle-Timeout ::= [28] INTEGER
Termination-Action ::= [29] INTEGER
Called-Station-Id ::= [30] UTF8String
Calling-Station-Id ::= [31] UTF8String
NAS-Identifier ::= [32] UTF8String
Proxy-State ::= [33] UTF8String
Login-LAT-Service ::= [34] UTF8String
Login-LAT-Node ::= [35] UTF8String
Login-LAT-Group ::= [36] UTF8String
Framed-AppleTalk-Link ::= [37] INTEGER
Framed-AppleTalk-Network ::= [38] INTEGER
Framed-AppleTalk-Zone ::= [39] UTF8String
CHAP-Challenge ::= [60] UTF8String
NAS-Port-Type ::= [61] INTEGER
Port-Limit ::= [62] INTEGER
Login-LAT-Port ::= [63] UTF8String
Acct-Status-Type ::= [40] INTEGER
Acct-Delay-Time ::= [41] INTEGER
Acct-Input-Octets ::= [42] INTEGER
Acct-Output-Octets ::= [43] INTEGER
Acct-Session-Id ::= [44] UTF8String
Acct-Authentic ::= [45] INTEGER
Acct-Session-Time ::= [46] INTEGER
Acct-Input-Packets ::= [47] INTEGER
Acct-Output-Packets ::= [48] INTEGER
Acct-Terminate-Cause ::= [49] INTEGER
Acct-Multi-Session-Id ::= [50] UTF8String
Acct-Link-Count ::= [51] INTEGER
Acct-Input-Gigawords ::= [52] INTEGER
Acct-Output-Gigawords ::= [53] INTEGER
Event-Timestamp ::= [55] INTEGER
ARAP-Password ::= [70] UTF8String
ARAP-Features ::= [71] UTF8String
ARAP-Zone-Access ::= [72] INTEGER
ARAP-Security ::= [73] INTEGER
ARAP-Security-Data ::= [74] UTF8String
Password-Retry ::= [75] INTEGER
Prompt ::= [76] INTEGER
Connect-Info ::= [77] UTF8String
Configuration-Token ::= [78] UTF8String
EAP-Message ::= [79] UTF8String
Message-Authenticator ::= [80] UTF8String
ARAP-Challenge-Response ::= [84] UTF8String
Acct-Interim-Interval ::= [85] INTEGER
NAS-Port-Id ::= [87] UTF8String
Framed-Pool ::= [88] UTF8String
SetupTime ::= [294937] UTF8String
ConnectTime ::= [294940] UTF8String
DisconnectTime ::= [294941] UTF8String
DisconnectCause ::= [294942] UTF8String
Acme-FlowID-FS1-F ::= [299761665] UTF8String
Acme-FlowType-FS1-F ::= [299761666] UTF8String
Acme-Session-Ingress-CallId ::= [299761667] UTF8String
Acme-Session-Egress-CallId ::= [299761668] UTF8String
Acme-Flow-In-Realm-FS1-F ::= [299761674] UTF8String
Acme-Flow-In-Src-Addr-FS1-F ::= [299761675] Address32
Acme-Flow-In-Src-Port-FS1-F ::= [299761676] INTEGER
Acme-Flow-In-Dst-Addr-FS1-F ::= [299761677] Address32
Acme-Flow-In-Dst-Port-FS1-F ::= [299761678] INTEGER
Acme-Flow-Out-Realm-FS1-F ::= [299761684] UTF8String
Acme-Flow-Out-Src-Addr-FS1-F ::= [299761685] Address32
Acme-Flow-Out-Src-Port-FS1-F ::= [299761686] INTEGER
Acme-Flow-Out-Dst-Addr-FS1-F ::= [299761687] Address32
Acme-Flow-Out-Dst-Port-FS1-F ::= [299761688] INTEGER
Acme-Calling-Octets-FS1 ::= [299761692] INTEGER
Acme-Calling-Packets-FS1 ::= [299761693] INTEGER
Acme-Calling-RTCP-Packets-Lost-FS1 ::= [299761696] INTEGER
Acme-Calling-RTCP-Avg-Jitter-FS1 ::= [299761697] INTEGER
Acme-Calling-RTCP-Avg-Latency-FS1 ::= [299761698] INTEGER
Acme-Calling-RTCP-MaxJitter-FS1 ::= [299761699] INTEGER
Acme-Calling-RTCP-MaxLatency-FS1 ::= [299761700] INTEGER
Acme-Calling-RTP-Packets-Lost-FS1 ::= [299761701] INTEGER
Acme-Calling-RTP-Avg-Jitter-FS1 ::= [299761702] INTEGER
Acme-Calling-RTP-MaxJitter-FS1 ::= [299761703] INTEGER
Acme-Session-Generic-Id ::= [299761704] UTF8String
Acme-Session-Ingress-Realm ::= [299761705] UTF8String
Acme-Session-Egress-Realm ::= [299761706] UTF8String
Acme-Session-Protocol-Type ::= [299761707] UTF8String
Acme-Called-Octets-FS1 ::= [299761708] INTEGER
Acme-Called-Packets-FS1 ::= [299761709] INTEGER
Acme-Called-RTCP-Packets-Lost-FS1 ::= [299761710] INTEGER
Acme-Called-RTCP-Avg-Jitter-FS1 ::= [299761711] INTEGER
Acme-Called-RTCP-Avg-Latency-FS1 ::= [299761712] INTEGER
Acme-Called-RTCP-MaxJitter-FS1 ::= [299761713] INTEGER
Acme-Called-RTCP-MaxLatency-FS1 ::= [299761714] INTEGER
Acme-Called-RTP-Packets-Lost-FS1 ::= [299761715] INTEGER
Acme-Called-RTP-Avg-Jitter-FS1 ::= [299761716] INTEGER
Acme-Called-RTP-MaxJitter-FS1 ::= [299761717] INTEGER
Acme-Session-Charging-Vector ::= [299761718] UTF8String
Acme-Session-Charging-Function-Address ::= [299761719] UTF8String
Acme-Firmware-Version ::= [299761720] UTF8String
Acme-Local-Time-Zone ::= [299761721] UTF8String
Acme-Post-Dial-Delay ::= [299761722] INTEGER
Acme-CDR-Sequence-Number ::= [299761723] INTEGER
Acme-Session-Disposition ::= [299761724] INTEGER
Acme-Disconnect-Initiator ::= [299761725] INTEGER
Acme-Disconnect-Cause ::= [299761726] INTEGER
Acme-Intermediate-Time ::= [299761727] UTF8String
Acme-Primary-Routing-Number ::= [299761728] UTF8String
Acme-Originating-Trunk-Group ::= [299761729] UTF8String
Acme-Terminating-Trunk-Group ::= [299761730] UTF8String
Acme-Originating-Trunk-Context ::= [299761731] UTF8String
Acme-Terminating-Trunk-Context ::= [299761732] UTF8String
Acme-P-Asserted-ID ::= [299761733] UTF8String
Acme-SIP-Diversion ::= [299761734] UTF8String
Acme-SIP-Status ::= [299761735] INTEGER
Acme-Ingress-Local-Addr ::= [299761738] UTF8String
Acme-Ingress-Remote-Addr ::= [299761739] UTF8String
Acme-Egress-Local-Addr ::= [299761740] UTF8String
Acme-Egress-Remote-Addr ::= [299761741] UTF8String
Acme-FlowID-FS1-R ::= [299761742] UTF8String
Acme-FlowType-FS1-R ::= [299761743] UTF8String
Acme-Flow-In-Realm-FS1-R ::= [299761744] UTF8String
Acme-Flow-In-Src-Addr-FS1-R ::= [299761745] Address32
Acme-Flow-In-Src-Port-FS1-R ::= [299761746] INTEGER
Acme-Flow-In-Dst-Addr-FS1-R ::= [299761747] Address32
Acme-Flow-In-Dst-Port-FS1-R ::= [299761748] INTEGER
Acme-Flow-Out-Realm-FS1-R ::= [299761749] UTF8String
Acme-Flow-Out-Src-Addr-FS1-R ::= [299761750] Address32
Acme-Flow-Out-Src-Port-FS1-R ::= [299761751] INTEGER
Acme-Flow-Out-Dst-Addr-FS1-R ::= [299761752] Address32
Acme-Flow-Out-Dst-Port-FS1-R ::= [299761753] INTEGER
Acme-FlowID-FS2-F ::= [299761754] UTF8String
Acme-FlowType-FS2-F ::= [299761755] UTF8String
Acme-Flow-In-Realm-FS2-F ::= [299761756] UTF8String
Acme-Flow-In-Src-Addr-FS2-F ::= [299761757] Address32
Acme-Flow-In-Src-Port-FS2-F ::= [299761758] INTEGER
Acme-Flow-In-Dst-Addr-FS2-F ::= [299761759] Address32
Acme-Flow-In-Dst-Port-FS2-F ::= [299761760] INTEGER
Acme-Flow-Out-Realm-FS2-F ::= [299761761] UTF8String
Acme-Flow-Out-Src-Addr-FS2-F ::= [299761762] Address32
Acme-Flow-Out-Src-Port-FS2-F ::= [299761763] INTEGER
Acme-Flow-Out-Dst-Addr-FS2-F ::= [299761764] Address32
Acme-Flow-Out-Dst-Port-FS2-F ::= [299761765] INTEGER
Acme-Calling-Octets-FS2 ::= [299761766] INTEGER
Acme-Calling-Packets-FS2 ::= [299761767] INTEGER
Acme-Calling-RTCP-Packets-Lost-FS2 ::= [299761768] INTEGER
Acme-Calling-RTCP-Avg-Jitter-FS2 ::= [299761769] INTEGER
Acme-Calling-RTCP-Avg-Latency-FS2 ::= [299761770] INTEGER
Acme-Calling-RTCP-MaxJitter-FS2 ::= [299761771] INTEGER
Acme-Calling-RTCP-MaxLatency-FS2 ::= [299761772] INTEGER
Acme-Calling-RTP-Packets-Lost-FS2 ::= [299761773] INTEGER
Acme-Calling-RTP-Avg-Jitter-FS2 ::= [299761774] INTEGER
Acme-Calling-RTP-MaxJitter-FS2 ::= [299761775] INTEGER
Acme-FlowID-FS2-R ::= [299761776] UTF8String
Acme-FlowType-FS2-R ::= [299761777] UTF8String
Acme-Flow-In-Realm-FS2-R ::= [299761778] UTF8String
Acme-Flow-In-Src-Addr-FS2-R ::= [299761779] Address32
Acme-Flow-In-Src-Port-FS2-R ::= [299761780] INTEGER
Acme-Flow-In-Dst-Addr-FS2-R ::= [299761781] Address32
Acme-Flow-In-Dst-Port-FS2-R ::= [299761782] INTEGER
Acme-Flow-Out-Realm-FS2-R ::= [299761783] UTF8String
Acme-Flow-Out-Src-Addr-FS2-R ::= [299761784] Address32
Acme-Flow-Out-Src-Port-FS2-R ::= [299761785] INTEGER
Acme-Flow-Out-Dst-Addr-FS2-R ::= [299761786] Address32
Acme-Flow-Out-Dst-Port-FS2-R ::= [299761787] INTEGER
Acme-Called-Octets-FS2 ::= [299761788] INTEGER
Acme-Called-Packets-FS2 ::= [299761789] INTEGER
Acme-Called-RTCP-Packets-Lost-FS2 ::= [299761790] INTEGER
Acme-Called-RTCP-Avg-Jitter-FS2 ::= [299761791] INTEGER
Acme-Called-RTCP-Avg-Latency-FS2 ::= [299761792] INTEGER
Acme-Called-RTCP-MaxJitter-FS2 ::= [299761793] INTEGER
Acme-Called-RTCP-MaxLatency-FS2 ::= [299761794] INTEGER
Acme-Called-RTP-Packets-Lost-FS2 ::= [299761795] INTEGER
Acme-Called-RTP-Avg-Jitter-FS2 ::= [299761796] INTEGER
Acme-Called-RTP-MaxJitter-FS2 ::= [299761797] INTEGER
Acme-Egress-Final-Routing-Number ::= [299761798] UTF8String
Acme-Session-Ingress-RPH ::= [299761799] UTF8String
Acme-Session-Egress-RPH ::= [299761800] UTF8String
Acme-Ingress-Network-Interface-Id ::= [299761801] UTF8String
Acme-Ingress-Vlan-Tag-Value ::= [299761802] INTEGER
Acme-Egress-Network-Interface-Id ::= [299761803] UTF8String
Acme-Egress-Vlan-Tag-Value ::= [299761804] INTEGER
Acme-Refer-Call-Transfer-Id ::= [299761805] UTF8String
Acme-Calling-R-Factor ::= [299761815] INTEGER
Acme-Calling-MOS ::= [299761816] INTEGER
Acme-Called-R-Factor ::= [299761817] INTEGER
Acme-Called-MOS ::= [299761818] INTEGER
Acme-Flow-In-Src-IPv6-Addr-FS1-F ::= [299761819] Address128
Acme-Flow-In-Dst-IPv6-Addr-FS1-F ::= [299761820] Address128
Acme-Flow-Out-Src-IPv6-Addr-FS1-F ::= [299761821] Address128
Acme-Flow-Out-Dst-IPv6-Addr-FS1-F ::= [299761822] Address128
Acme-Flow-In-Src-IPv6-Addr-FS1-R ::= [299761823] Address128
Acme-Flow-In-Dst-IPv6-Addr-FS1-R ::= [299761824] Address128
Acme-Flow-Out-Src-IPv6-Addr-FS1-R ::= [299761825] Address128
Acme-Flow-Out-Dst-IPv6-Addr-FS1-R ::= [299761826] Address128
Acme-Flow-In-Src-IPv6-Addr-FS2-F ::= [299761827] Address128
Acme-Flow-In-Dst-IPv6-Addr-FS2-F ::= [299761828] Address128
Acme-Flow-Out-Src-IPv6-Addr-FS2-F ::= [299761829] Address128
Acme-Flow-Out-Dst-IPv6-Addr-FS2-F ::= [299761830] Address128
Acme-Flow-In-Src-IPv6-Addr-FS2-R ::= [299761831] Address128
Acme-Flow-In-Dst-IPv6-Addr-FS2-R ::= [299761832] Address128
Acme-Flow-Out-Src-IPv6-Addr-FS2-R ::= [299761833] Address128
Acme-Flow-Out-Dst-IPv6-Addr-FS2-R ::= [299761834] Address128
Acme-Session-Forked-Call-Id ::= [299761835] UTF8String
Acme-Custom-VSA-200 ::= [299761864] UTF8String
Acme-Custom-VSA-201 ::= [299761865] UTF8String
Acme-Custom-VSA-202 ::= [299761866] UTF8String
Acme-Custom-VSA-203 ::= [299761867] UTF8String
Acme-Custom-VSA-204 ::= [299761868] UTF8String
Acme-Custom-VSA-205 ::= [299761869] UTF8String
Acme-Custom-VSA-206 ::= [299761870] UTF8String
Acme-Custom-VSA-207 ::= [299761871] UTF8String
Acme-Custom-VSA-208 ::= [299761872] UTF8String
Acme-Custom-VSA-209 ::= [299761873] UTF8String
Acme-Custom-VSA-210 ::= [299761874] UTF8String
Acme-Custom-VSA-211 ::= [299761875] UTF8String
Acme-Custom-VSA-212 ::= [299761876] UTF8String
Acme-Custom-VSA-213 ::= [299761877] UTF8String
Acme-Custom-VSA-214 ::= [299761878] UTF8String
Acme-Custom-VSA-215 ::= [299761879] UTF8String
Acme-Custom-VSA-216 ::= [299761880] UTF8String
Acme-Custom-VSA-217 ::= [299761881] UTF8String
Acme-Custom-VSA-218 ::= [299761882] UTF8String
Acme-Custom-VSA-219 ::= [299761883] UTF8String
Acme-Custom-VSA-220 ::= [299761884] UTF8String
Acme-Custom-VSA-221 ::= [299761885] UTF8String
Acme-Custom-VSA-222 ::= [299761886] UTF8String
Acme-Custom-VSA-223 ::= [299761887] UTF8String
Acme-Custom-VSA-224 ::= [299761888] UTF8String
Acme-Custom-VSA-225 ::= [299761889] UTF8String
Acme-Custom-VSA-226 ::= [299761890] UTF8String
Acme-Custom-VSA-227 ::= [299761891] UTF8String
Acme-Custom-VSA-228 ::= [299761892] UTF8String
Acme-Custom-VSA-229 ::= [299761893] UTF8String
Acme-Custom-VSA-230 ::= [299761894] UTF8String
Acme-Flow-Calling-Media-Stop-Time-FS1 ::= [299761895] UTF8String
Acme-Flow-Called-Media-Stop-Time-FS1 ::= [299761896] UTF8String
Acme-Flow-Calling-Media-Stop-Time-FS2 ::= [299761897] UTF8String
Acme-Flow-Called-Media-Stop-Time-FS2 ::= [299761898] UTF8String
Acme-User-Class ::= [299761918] UTF8String
END
